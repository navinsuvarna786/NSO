module hostname {
  namespace "http://com/example/hostname";
  prefix hostname;

  import ietf-inet-types {
    prefix inet;
  }
  import tailf-ncs {
    prefix ncs;
  }
  import tailf-common {
    prefix tailf;
  }

  list hostname {
    key device;

    uses ncs:service-data;
    ncs:servicepoint "hostname";

    leaf device {
      type leafref {
        path "/ncs:devices/ncs:device/ncs:name";
      }
    }

    leaf hostname {
      tailf:info "Device hostname";
      type string;
    }

  }
}
