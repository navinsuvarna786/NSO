module esc_vim_connector {
  // Generated by yanger -t ncs
  tailf:mount-id esc-nc-1.0:esc-nc-1.0;
  tailf:ncs-device-type "netconf";

  namespace "http://www.cisco.com/esc/esc_vim_connector";
  prefix esc_vim_connector;

  import esc_types {
    prefix types;
  }
  import esc_property {
    prefix property;
  }
  import "esc-nc-1.0" {
    prefix "esc-nc-1.0";
  }
  import tailf-ncs {
    prefix ncs;
  }
  import tailf-common {
    prefix tailf;
  }

  organization
    "Cisco Systems";
  contact
    "Natasha Shrestha <nashrestha@cisco.com>";
  description
    "VIM and vim users configured in ESC.";

  revision 2018-05-10 {
    description
      "adding connector leaf vim_type type KUBERNETES";
  }
  revision 2017-04-25 {
    description
      "adding default connector leaf";
  }
  revision 2016-09-23 {
    description
      "VIM Connector";
  }

  grouping ncs_template_esc_vim_connector {
    container vim_connectors {
      leaf default_vim_connector {
        type string;
      }
      list vim_connector {
        // NCS patched for predictable order
        ordered-by user;
        key "id";
        description
          "List of vim connectors.";
        leaf id {
          description
            "A unique id to represent a VIM connection.";
          type types:ncs_template_escname;
          // NCS drop mandatory statement
        }
        leaf type {
          description
            "Type of VIM: OPENSTACK, LIBVIRT, VMWARE_VSPHERE, AWS_EC2, KUBERNETES, CCP";
          type types:ncs_template_vim_type;
          // NCS drop mandatory statement
        }
        uses property:ncs_template_property_list_definition;
        uses ncs_template_esc_vim_users;
      }
    }
  }

  grouping ncs_template_esc_vim_users {
    container users {
      list user {
        // NCS patched for predictable order
        ordered-by user;
        key "id";
        description
          "List of vim users";
        leaf id {
          description
            "Unique id for user. This id is also used as username for
             user-password based authentication";
          type string;
          // NCS drop mandatory statement
        }
        container credentials {
          description
            "Specify authentication credentials of a vim user. Key value based
             properties can be used to specify password, certificate, access_key
             etc.";
          uses property:ncs_template_property_list_definition;
        }
      }
    }
  }

  grouping ncs_rpc_notif_esc_vim_connector {
    container vim_connectors {
      leaf default_vim_connector {
        type leafref {
          path "../vim_connector/id";
        }
      }
      list vim_connector {
        key "id";
        description
          "List of vim connectors.";
        leaf id {
          description
            "A unique id to represent a VIM connection.";
          type types:ncs_rpc_notif_escname;
          mandatory true;
        }
        leaf type {
          description
            "Type of VIM: OPENSTACK, LIBVIRT, VMWARE_VSPHERE, AWS_EC2, KUBERNETES, CCP";
          type types:ncs_rpc_notif_vim_type;
          mandatory true;
        }
        uses property:ncs_rpc_notif_property_list_definition;
        uses ncs_rpc_notif_esc_vim_users;
      }
    }
  }

  grouping ncs_rpc_notif_esc_vim_users {
    container users {
      list user {
        key "id";
        description
          "List of vim users";
        leaf id {
          description
            "Unique id for user. This id is also used as username for
             user-password based authentication";
          type string;
          mandatory true;
        }
        container credentials {
          description
            "Specify authentication credentials of a vim user. Key value based
             properties can be used to specify password, certificate, access_key
             etc.";
          uses property:ncs_rpc_notif_property_list_definition;
        }
      }
    }
  }

  grouping live_ncs_esc_vim_connector {
    container vim_connectors {
      leaf default_vim_connector {
        type leafref {
          path "../vim_connector/id";
        }
      }
      list vim_connector {
        key "id";
        description
          "List of vim connectors.";
        leaf id {
          description
            "A unique id to represent a VIM connection.";
          type types:live_ncs_escname;
          // NCS drop mandatory statement
        }
        leaf type {
          description
            "Type of VIM: OPENSTACK, LIBVIRT, VMWARE_VSPHERE, AWS_EC2, KUBERNETES, CCP";
          type types:live_ncs_vim_type;
          // NCS drop mandatory statement
        }
        uses property:live_ncs_property_list_definition;
        uses live_ncs_esc_vim_users;
      }
    }
  }

  grouping live_ncs_esc_vim_users {
    container users {
      list user {
        key "id";
        description
          "List of vim users";
        leaf id {
          description
            "Unique id for user. This id is also used as username for
             user-password based authentication";
          type string;
          // NCS drop mandatory statement
        }
        container credentials {
          description
            "Specify authentication credentials of a vim user. Key value based
             properties can be used to specify password, certificate, access_key
             etc.";
          uses property:live_ncs_property_list_definition;
        }
      }
    }
  }

  grouping esc_vim_connector {
    container vim_connectors {
      leaf default_vim_connector {
        type leafref {
          path "../vim_connector/id";
        }
      }
      list vim_connector {
        key "id";
        description
          "List of vim connectors.";
        leaf id {
          description
            "A unique id to represent a VIM connection.";
          type types:escname;
          mandatory true;
        }
        leaf type {
          description
            "Type of VIM: OPENSTACK, LIBVIRT, VMWARE_VSPHERE, AWS_EC2, KUBERNETES, CCP";
          type types:vim_type;
          mandatory true;
        }
        uses property:property_list_definition;
        uses esc_vim_users;
      }
    }
  }

  grouping esc_vim_users {
    container users {
      list user {
        key "id";
        description
          "List of vim users";
        leaf id {
          description
            "Unique id for user. This id is also used as username for
             user-password based authentication";
          type string;
          mandatory true;
        }
        container credentials {
          description
            "Specify authentication credentials of a vim user. Key value based
             properties can be used to specify password, certificate, access_key
             etc.";
          uses property:property_list_definition;
        }
      }
    }
  }
}
