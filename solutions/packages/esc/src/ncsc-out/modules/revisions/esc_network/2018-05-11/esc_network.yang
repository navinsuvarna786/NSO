module esc_network {
  // Generated by yanger -t ncs
  tailf:mount-id esc-nc-1.0:esc-nc-1.0;
  tailf:ncs-device-type "netconf";

  namespace "http://www.cisco.com/esc/esc_network";
  prefix esc_network;

  import esc_types {
    prefix types;
  }
  import esc_locators {
    prefix locators;
  }
  import "esc-nc-1.0" {
    prefix "esc-nc-1.0";
  }
  import tailf-ncs {
    prefix ncs;
  }
  import tailf-common {
    prefix tailf;
  }

  organization
    "Cisco Systems";
  contact
    "Shesha Sreenivasamurthy <shesha@cisco.com>";
  description
    "ESC's Network descriptions'";

  revision 2018-05-11 {
    description
      "Added multi_vim_locators case to locators block";
  }
  revision 2016-03-16 {
    description
      "Added locator source block for vim-specific locators";
  }
  revision 2016-02-04 {
    description
      "Added no_gateway to subnet";
  }
  revision 2015-12-02 {
    description
      "Added switch_name, vlan_id, number_of_ports to network";
  }
  revision 2015-08-05 {
    description
      " Added router:external attribute for networks ";
  }
  revision 2015-07-02 {
    description
      "change to remove default value for provider_segmentation_id as it is not required to have a default";
  }
  revision 2015-06-29 {
    description
      "ESC Networks change to add provider_network attributes and remove vlanID attribute";
  }
  revision 2014-06-23 {
    description
      "ESC Networks";
  }

  grouping ncs_template_esc_network {
    container networks {
      description
        "These are the 'Ephemeral' networks that will be created
         and destroyed during deployment. Usually these are internal
         network for that service which may be used for
         communication between VMs in this service.";
      list network {
        // NCS patched for predictable order
        ordered-by user;
        key "name";
        leaf name {
          description
            "Name of the network to be created.
             The name will be appended with the
             deployment id during actual creation during deployment to
             maintain uniqueness. These are given before vm_group so
             that ESC can create the network before actually deploying
             any VMs on the network in one pass.";
          type types:ncs_template_escnetname;
          // NCS drop mandatory statement
        }
        leaf shared {
          description
            "Whether the network is shared among other tenants";
          type string;
          // NCS drop default statement
        }
        leaf admin_state {
          description
            "Specifies whether the admin state is up or down. Set to true for up
             and false for down. If down, the network does not forward
             packets.";
          type string;
          // NCS drop default statement
        }
        leaf router_external {
          description
            "Indicates whether this network is externally accessible.";
          type string;
        }
        leaf provider_physical_network {
          description
            "Specifies the name of the physical network
             over which the virtual network is implemented.";
          type string;
        }
        leaf provider_network_type {
          description
            "Specifies the physical mechanism by which
             the Virtual network is implemented.";
          type string;
        }
        leaf provider_segmentation_id {
          description
            "ID or tunnel ID of the underlying physical network";
          type string;
        }
        choice locator-source {
          case legacy {
            leaf switch_name {
              description
                "(VMWare only) Specifies the name of the switch";
              type string;
            }
          }
          case locators {
            uses locators:ncs_template_extensible_locators;
          }
          case multi_vim_locators {
            leaf vim_network_name {
              description
                "Specifies the name of the network to be created on the VIM";
              // NCS drop must statement
              // NCS drop must statement
              type types:ncs_template_escnetname;
            }
            uses locators:ncs_template_network_vim_locators;
          }
        }
        leaf vlan_id {
          description
            "(VMWare only) Specifies the vlan id to assign to this port group";
          type string;
        }
        leaf number_of_ports {
          description
            "(VMWare only) Specifies the number of ports to allocate on the port group";
          type string;
        }
        list subnet {
          // NCS patched for predictable order
          ordered-by user;
          key "name";
          leaf name {
            description
              "Name of the subnet";
            type types:ncs_template_escnetname;
            // NCS drop mandatory statement
          }
          leaf ipversion {
            description
              "Size of the Volume";
            type types:ncs_template_ipversion_t;
            // NCS drop default statement
          }
          leaf dhcp {
            description
              "Are IP address for the VMs on this network are
               to be allocated by DHCP";
            type string;
            // NCS drop default statement
          }
          leaf address {
            description
              "Subnet address for this network. Eg: 10.4.4.0";
            type types:ncs_template_escipaddr;
            // NCS drop mandatory statement
          }
          leaf netmask {
            description
              "Subnet mask represented by IP address";
            type types:ncs_template_escipaddr;
          }
          leaf ip_prefix {
            description
              "Subnet mask represented by IP prefix.
               For IPv4 subnet, it is 0 - 32. For IPv6
               subnet, it is 0 - 128.";
            type types:ncs_template_esc_ip_prefix;
          }
          leaf gateway {
            description
              "Default GW for the network. If un specified ESC will try
               to determine the gateway for the network.";
            type types:ncs_template_escipaddr;
          }
          leaf no_gateway {
            description
              "no gateway for the network. It will ignore gateway setting";
            type string;
            // NCS drop default statement
          }
        }
      }
    }
  }

  grouping ncs_rpc_notif_esc_network {
    container networks {
      description
        "These are the 'Ephemeral' networks that will be created
         and destroyed during deployment. Usually these are internal
         network for that service which may be used for
         communication between VMs in this service.";
      list network {
        key "name";
        leaf name {
          description
            "Name of the network to be created.
             The name will be appended with the
             deployment id during actual creation during deployment to
             maintain uniqueness. These are given before vm_group so
             that ESC can create the network before actually deploying
             any VMs on the network in one pass.";
          type types:ncs_rpc_notif_escnetname;
          mandatory true;
        }
        leaf shared {
          description
            "Whether the network is shared among other tenants";
          type boolean;
          default "true";
        }
        leaf admin_state {
          description
            "Specifies whether the admin state is up or down. Set to true for up
             and false for down. If down, the network does not forward
             packets.";
          type boolean;
          default "true";
        }
        leaf router_external {
          description
            "Indicates whether this network is externally accessible.";
          type boolean;
        }
        leaf provider_physical_network {
          description
            "Specifies the name of the physical network
             over which the virtual network is implemented.";
          type string;
        }
        leaf provider_network_type {
          description
            "Specifies the physical mechanism by which
             the Virtual network is implemented.";
          type string;
        }
        leaf provider_segmentation_id {
          description
            "ID or tunnel ID of the underlying physical network";
          type uint32;
        }
        choice locator-source {
          case legacy {
            leaf switch_name {
              description
                "(VMWare only) Specifies the name of the switch";
              type string;
            }
          }
          case locators {
            uses locators:ncs_rpc_notif_extensible_locators;
          }
          case multi_vim_locators {
            leaf vim_network_name {
              description
                "Specifies the name of the network to be created on the VIM";
              must "../../../../../vim_mapping[text()='false']" {
                tailf:xpath-root 3;
                error-message "tenant vim_mapping must be set to false";
              }
              must 'boolean(../locator/vim_id)' {
                tailf:xpath-root 3;
                error-message "locator/vim_id is required";
              }
              type types:ncs_rpc_notif_escnetname;
            }
            uses locators:ncs_rpc_notif_network_vim_locators;
          }
        }
        leaf vlan_id {
          description
            "(VMWare only) Specifies the vlan id to assign to this port group";
          type uint32;
        }
        leaf number_of_ports {
          description
            "(VMWare only) Specifies the number of ports to allocate on the port group";
          type uint32;
        }
        list subnet {
          key "name";
          leaf name {
            description
              "Name of the subnet";
            type types:ncs_rpc_notif_escnetname;
            mandatory true;
          }
          leaf ipversion {
            description
              "Size of the Volume";
            type types:ncs_rpc_notif_ipversion_t;
            default "ipv4";
          }
          leaf dhcp {
            description
              "Are IP address for the VMs on this network are
               to be allocated by DHCP";
            type boolean;
            default "true";
          }
          leaf address {
            description
              "Subnet address for this network. Eg: 10.4.4.0";
            type types:ncs_rpc_notif_escipaddr;
            mandatory true;
          }
          leaf netmask {
            description
              "Subnet mask represented by IP address";
            type types:ncs_rpc_notif_escipaddr;
          }
          leaf ip_prefix {
            description
              "Subnet mask represented by IP prefix.
               For IPv4 subnet, it is 0 - 32. For IPv6
               subnet, it is 0 - 128.";
            type types:ncs_rpc_notif_esc_ip_prefix;
          }
          leaf gateway {
            description
              "Default GW for the network. If un specified ESC will try
               to determine the gateway for the network.";
            type types:ncs_rpc_notif_escipaddr;
          }
          leaf no_gateway {
            description
              "no gateway for the network. It will ignore gateway setting";
            type boolean;
            default "false";
          }
        }
      }
    }
  }

  grouping live_ncs_esc_network {
    container networks {
      description
        "These are the 'Ephemeral' networks that will be created
         and destroyed during deployment. Usually these are internal
         network for that service which may be used for
         communication between VMs in this service.";
      list network {
        key "name";
        leaf name {
          description
            "Name of the network to be created.
             The name will be appended with the
             deployment id during actual creation during deployment to
             maintain uniqueness. These are given before vm_group so
             that ESC can create the network before actually deploying
             any VMs on the network in one pass.";
          type types:live_ncs_escnetname;
          // NCS drop mandatory statement
        }
        leaf shared {
          description
            "Whether the network is shared among other tenants";
          type boolean;
          // NCS drop default statement
        }
        leaf admin_state {
          description
            "Specifies whether the admin state is up or down. Set to true for up
             and false for down. If down, the network does not forward
             packets.";
          type boolean;
          // NCS drop default statement
        }
        leaf router_external {
          description
            "Indicates whether this network is externally accessible.";
          type boolean;
        }
        leaf provider_physical_network {
          description
            "Specifies the name of the physical network
             over which the virtual network is implemented.";
          type string;
        }
        leaf provider_network_type {
          description
            "Specifies the physical mechanism by which
             the Virtual network is implemented.";
          type string;
        }
        leaf provider_segmentation_id {
          description
            "ID or tunnel ID of the underlying physical network";
          type uint32;
        }
        choice locator-source {
          case legacy {
            leaf switch_name {
              description
                "(VMWare only) Specifies the name of the switch";
              type string;
            }
          }
          case locators {
            uses locators:live_ncs_extensible_locators;
          }
          case multi_vim_locators {
            leaf vim_network_name {
              description
                "Specifies the name of the network to be created on the VIM";
              // NCS drop must statement
              // NCS drop must statement
              type types:live_ncs_escnetname;
            }
            uses locators:live_ncs_network_vim_locators;
          }
        }
        leaf vlan_id {
          description
            "(VMWare only) Specifies the vlan id to assign to this port group";
          type uint32;
        }
        leaf number_of_ports {
          description
            "(VMWare only) Specifies the number of ports to allocate on the port group";
          type uint32;
        }
        list subnet {
          key "name";
          leaf name {
            description
              "Name of the subnet";
            type types:live_ncs_escnetname;
            // NCS drop mandatory statement
          }
          leaf ipversion {
            description
              "Size of the Volume";
            type types:live_ncs_ipversion_t;
            // NCS drop default statement
          }
          leaf dhcp {
            description
              "Are IP address for the VMs on this network are
               to be allocated by DHCP";
            type boolean;
            // NCS drop default statement
          }
          leaf address {
            description
              "Subnet address for this network. Eg: 10.4.4.0";
            type types:live_ncs_escipaddr;
            // NCS drop mandatory statement
          }
          leaf netmask {
            description
              "Subnet mask represented by IP address";
            type types:live_ncs_escipaddr;
          }
          leaf ip_prefix {
            description
              "Subnet mask represented by IP prefix.
               For IPv4 subnet, it is 0 - 32. For IPv6
               subnet, it is 0 - 128.";
            type types:live_ncs_esc_ip_prefix;
          }
          leaf gateway {
            description
              "Default GW for the network. If un specified ESC will try
               to determine the gateway for the network.";
            type types:live_ncs_escipaddr;
          }
          leaf no_gateway {
            description
              "no gateway for the network. It will ignore gateway setting";
            type boolean;
            // NCS drop default statement
          }
        }
      }
    }
  }

  grouping esc_network {
    container networks {
      description
        "These are the 'Ephemeral' networks that will be created
         and destroyed during deployment. Usually these are internal
         network for that service which may be used for
         communication between VMs in this service.";
      list network {
        key "name";
        leaf name {
          description
            "Name of the network to be created.
             The name will be appended with the
             deployment id during actual creation during deployment to
             maintain uniqueness. These are given before vm_group so
             that ESC can create the network before actually deploying
             any VMs on the network in one pass.";
          type types:escnetname;
          mandatory true;
        }
        leaf shared {
          description
            "Whether the network is shared among other tenants";
          type boolean;
          default "true";
        }
        leaf admin_state {
          description
            "Specifies whether the admin state is up or down. Set to true for up
             and false for down. If down, the network does not forward
             packets.";
          type boolean;
          default "true";
        }
        leaf router_external {
          description
            "Indicates whether this network is externally accessible.";
          type boolean;
        }
        leaf provider_physical_network {
          description
            "Specifies the name of the physical network
             over which the virtual network is implemented.";
          type string;
        }
        leaf provider_network_type {
          description
            "Specifies the physical mechanism by which
             the Virtual network is implemented.";
          type string;
        }
        leaf provider_segmentation_id {
          description
            "ID or tunnel ID of the underlying physical network";
          type uint32;
        }
        choice locator-source {
          case legacy {
            leaf switch_name {
              description
                "(VMWare only) Specifies the name of the switch";
              type string;
            }
          }
          case locators {
            uses locators:extensible_locators;
          }
          case multi_vim_locators {
            leaf vim_network_name {
              description
                "Specifies the name of the network to be created on the VIM";
              must "../../../../../vim_mapping[text()='false']" {
                tailf:xpath-root 3;
                error-message "tenant vim_mapping must be set to false";
              }
              must 'boolean(../locator/vim_id)' {
                tailf:xpath-root 3;
                error-message "locator/vim_id is required";
              }
              type types:escnetname;
            }
            uses locators:network_vim_locators;
          }
        }
        leaf vlan_id {
          description
            "(VMWare only) Specifies the vlan id to assign to this port group";
          type uint32;
        }
        leaf number_of_ports {
          description
            "(VMWare only) Specifies the number of ports to allocate on the port group";
          type uint32;
        }
        list subnet {
          key "name";
          leaf name {
            description
              "Name of the subnet";
            type types:escnetname;
            mandatory true;
          }
          leaf ipversion {
            description
              "Size of the Volume";
            type types:ipversion_t;
            default "ipv4";
          }
          leaf dhcp {
            description
              "Are IP address for the VMs on this network are
               to be allocated by DHCP";
            type boolean;
            default "true";
          }
          leaf address {
            description
              "Subnet address for this network. Eg: 10.4.4.0";
            type types:escipaddr;
            mandatory true;
          }
          leaf netmask {
            description
              "Subnet mask represented by IP address";
            type types:escipaddr;
          }
          leaf ip_prefix {
            description
              "Subnet mask represented by IP prefix.
               For IPv4 subnet, it is 0 - 32. For IPv6
               subnet, it is 0 - 128.";
            type types:esc_ip_prefix;
          }
          leaf gateway {
            description
              "Default GW for the network. If un specified ESC will try
               to determine the gateway for the network.";
            type types:escipaddr;
          }
          leaf no_gateway {
            description
              "no gateway for the network. It will ignore gateway setting";
            type boolean;
            default "false";
          }
        }
      }
    }
  }
}
