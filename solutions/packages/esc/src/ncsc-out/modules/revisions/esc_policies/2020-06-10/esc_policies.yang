module esc_policies {
  // Generated by yanger -t ncs
  tailf:mount-id esc-nc-1.0:esc-nc-1.0;
  tailf:ncs-device-type "netconf";

  namespace "http://www.cisco.com/esc/esc_policies";
  prefix esc_policies;

  import esc_types {
    prefix types;
  }
  import esc_property {
    prefix property;
  }
  import esc_file_locators {
    prefix file_locators;
  }
  import "esc-nc-1.0" {
    prefix "esc-nc-1.0";
  }
  import tailf-ncs {
    prefix ncs;
  }
  import tailf-common {
    prefix tailf;
  }

  organization
    "Cisco Systems";
  contact
    "Shesha Sreenivasamurthy <shesha@cisco.com>";
  description
    "ESC's Policy descriptions. This refers to external_dependency Policy
     or VM placement policy or if a service has multiple VMs, then it
     may be start-up policy that determines the sequence in which the
     VMs are started.";

  revision 2020-06-10 {
    description
      "Added vmexportpolicy";
  }
  revision 2020-02-03 {
    description
      "Updated zone_host type as host_location_type";
  }
  revision 2019-02-11 {
    description
      "Added new leaf monitor_on_error to enable continuous monitor of VM on error state";
  }
  revision 2018-02-11 {
    description
      "Added new type host_location_type for zone_host";
  }
  revision 2017-11-16 {
    description
      "Deprecate file_locators to allow use of deployment defined file_locators";
  }
  revision 2017-09-01 {
    description
      "Added file_locators to esc_policy -> actions container to support remote/local file retrieval.";
  }
  revision 2016-10-18 {
    description
      "Update placement_group description";
  }
  revision 2016-05-11 {
    description
      "Added placement_group to support new inter-group affinity/anti-affinity relationships";
  }
  revision 2016-05-11 {
    description
      "Added type as part of key of inter_vm_group_placement";
  }
  revision 2016-04-13 {
    description
      "Added a generic policy container to support condition/actions";
  }
  revision 2015-09-21 {
    description
      "Added a leaf to config if redeploy is needed after reboot fails upon recovery";
  }
  revision 2015-09-04 {
    description
      "modified to allow for target_vm_group_ref and vm_group_ref possibly having the same value ";
  }
  revision 2015-08-20 {
    description
      "change types= host_placement and zone_placement to zone_host";
  }
  revision 2015-08-12 {
    description
      "modified inter enforcement to have a default value: strict";
  }
  revision 2015-08-11 {
    description
      "modified enforcement to have a default value: strict";
  }
  revision 2015-07-24 {
    description
      "Added types= host_placement and zone_placement";
  }
  revision 2015-07-07 {
    description
      "Added availability zone as a choice";
  }
  revision 2014-06-23 {
    description
      "ESC Dependencies";
  }

  grouping ncs_template_svc_dependency {
    container service_dependency {
      description
        "These are the services that needs to be running. Eg dns, syslog";
      list service {
        // NCS patched for predictable order
        ordered-by user;
        key "service_name service_version";
        leaf service_name {
          description
            "Dependent Service Name";
          type types:ncs_template_escname;
          // NCS drop mandatory statement
        }
        leaf service_version {
          description
            "Version of the dependent service";
          type types:ncs_template_escversion;
          // NCS drop mandatory statement
        }
      }
    }
  }

  grouping ncs_template_net_dependency {
    container network_dependency {
      description
        "Existence of these networks are checked but are not created if it does
         not. If the dependency is not met, registration of the
         service fails. This is a list. One can specify as may network
         dependencies as required. For example, external or management
         network. These networks has to be pre-created and when
         specifying the interfaces, the network to which its has to be
         connected is specified.";
      leaf-list network {
        // NCS patched for predictable order
        ordered-by user;
        description
          "Name of the dependent networks";
        type types:ncs_template_escnetname;
      }
    }
  }

  grouping ncs_template_placement_group {
    list placement_group {
      // NCS patched for predictable order
      ordered-by user;
      description
        "Placement group. Specifying it as a list allows us to
         define mutual relationship among different combination of vm_groups.";
      key "name";
      leaf name {
        description
          "Name of placement group";
        type string;
        // NCS drop mandatory statement
      }
      leaf type {
        description
          "affinity or anti_affinity";
        type types:ncs_template_placement_type;
        // NCS drop mandatory statement
      }
      leaf enforcement {
        description
          "Strict or Loose enforcement";
        type types:ncs_template_enforcement;
        // NCS drop default statement
      }
      leaf-list vm_group {
        // NCS patched for predictable order
        ordered-by user;
        type string;
        // NCS drop min-elements statement
      }
    }
  }

  grouping ncs_template_inter_vm_group_placement {
    list placement {
      // NCS patched for predictable order
      ordered-by user;
      description
        "Placement policy specification. Specifying it as a list allows us to
         define different placement policies among different
         combination of vm_groups";
      key "target_vm_group_ref type";
      leaf target_vm_group_ref {
        description
          "Name of the group whose VMs will be subjected to the placement
           rules specified below";
        type string;
      }
      leaf type {
        description
          "affinity or anti_affinity";
        type types:ncs_template_placement_type;
        // NCS drop mandatory statement
      }
      leaf enforcement {
        description
          "Strict or Loose enforcement";
        type types:ncs_template_enforcement;
        // NCS drop default statement
      }
      leaf-list vm_group_ref {
        // NCS patched for predictable order
        ordered-by user;
        type string;
        // NCS drop min-elements statement
      }
    }
  }

  grouping ncs_template_intra_vm_group_placement {
    list placement {
      // NCS patched for predictable order
      ordered-by user;
      description
        "Placement policy within a VM group. keying off of
         type as we cannot have same rule multiple times within
         the group.";
      key "type";
      leaf type {
        description
          "affinity, anti_affinity, zone_host";
        type types:ncs_template_placement_type;
        // NCS drop mandatory statement
      }
      leaf enforcement {
        description
          "Strict or Loose enforcement";
        type types:ncs_template_enforcement;
        // NCS drop default statement
      }
      choice zone_host {
        // NCS drop when statement
        case host {
          leaf host {
            description
              "Host on which the affinity rules specified above should be applied against the VMs of group specified above.";
            type types:ncs_template_host_location_type;
            // NCS drop mandatory statement
          }
        }
        case zone {
          leaf zone {
            description
              "The availability zone in which the vm group will be deployed";
            type types:ncs_template_escname;
            // NCS drop mandatory statement
          }
        }
      }
    }
  }

  grouping ncs_template_recovery_policies {
    container recovery_policy {
      description
        "Policy of recovery";
      leaf recovery_type {
        description
          "The type of recovery";
        type types:ncs_template_recovery_style_types;
        // NCS drop default statement
      }
      leaf action_on_recovery {
        description
          "The action performed during recovery";
        type types:ncs_template_recovery_action_types;
        // NCS drop default statement
      }
      leaf max_retries {
        description
          "The number of recovery attempts";
        type string;
      }
      leaf monitor_on_error {
        description
          "Continue monitoring of VM on error state.
           By Default monitoring is disabled on VM error state.
           When monitor_on_error flag is set to true, monitor is not disabled on error state and continues to monitor.";
        type string;
        // NCS drop default statement
      }
    }
  }

  grouping ncs_template_vmexport_policies {
    container vmexport_policy {
      description
        "Policy of vm export";
      list disk_exclusion {
        // NCS patched for predictable order
        ordered-by user;
        key "disk_name";
        leaf disk_name {
          description
            "The disk to exclude.  One of 'image name' /
             'image name:disk name' / 'volume name'";
          type string;
        }
      }
    }
  }

  grouping ncs_template_intra_vm_group_properties {
    list shared_ip {
      // NCS patched for predictable order
      ordered-by user;
      description
        "Shared Ip is the ip address that is assigned to the vm_group";
      key "nicid";
      leaf nicid {
        description
          "Interface where the static_ip property is applied.
           Ensure that interface with this ID is specified earlier";
        type string;
        // NCS drop mandatory statement
      }
      leaf static {
        description
          "Is the shared_ip static";
        type string;
        // NCS drop default statement
      }
      leaf ip_address {
        description
          "Static IP address for this interface";
        type types:ncs_template_escipaddr;
      }
    }
    container properties {
      description
        "List of key value pair to be passed to esc to
         configure the vmgroup properties. For example, key is NOTIFY_EXTERNAL_MONITOR
         and the value is ENABLED";
      list property {
        // NCS patched for predictable order
        ordered-by user;
        key "prop_key";
        leaf prop_key {
          description
            "key for the property";
          type types:ncs_template_vm_group_properties;
        }
        leaf prop_value {
          description
            "value of the property";
          type types:ncs_template_escbigdata;
        }
      }
    }
  }

  grouping ncs_template_esc_policies {
    container policies {
      description
        "Describes different policies that can be specified that will affect
         the way VMs are brought up.";
      container external_dependencies {
        description
          "Any dependencies such as service dependencies or network dependencies
           are listed in this section. If the dependencies are not
           met, then registration is rejected. This is used to check
           for the existence of service or network but will not be
           created if the services or network is not present.";
        uses ncs_template_svc_dependency;
        uses ncs_template_net_dependency;
      }
      uses ncs_template_placement_group;
      uses ncs_template_inter_vm_group_placement;
      list startup {
        // NCS patched for predictable order
        ordered-by user;
        description
          "Start up sequence specification. This is achieved at the granularity
           of vm group. It allows one to specify start up of a
           particular group of VMs depends on which other groups. When
           do we say that the dependent group have successfully brought
           up ? This is achieved by waiting for an event that is
           specified. Can be collection of events too.";
        key "target_vm_group_ref";
        leaf target_vm_group_ref {
          description
            "Name of the group whose VMs will be subjected to the placement
             rules specified below";
          type string;
        }
        list depends_on {
          // NCS patched for predictable order
          ordered-by user;
          key "vm_group_ref";
          leaf vm_group_ref {
            type string;
            // NCS drop mandatory statement
          }
          leaf-list kpi_event_ref {
            // NCS patched for predictable order
            ordered-by user;
            description
              "Here max and min elements is set to 1 as currently
               support only one event.";
            type string;
            // NCS drop min-elements statement
            // NCS drop max-elements statement
          }
        }
      }
      uses ncs_template_esc_policy;
    }
  }

  grouping ncs_template_esc_policy {
    list policy {
      // NCS patched for predictable order
      ordered-by user;
      description
        "The policy list that contains a list of conditions and a list of actions";
      key "name";
      leaf name {
        description
          "Unique policy name";
        type string;
      }
      container conditions {
        description
          "The lifecycle stage conditions to trigger actions";
        list condition {
          // NCS patched for predictable order
          ordered-by user;
          key "name";
          leaf name {
            description
              "Unique condition type";
            type types:ncs_template_policy_condition_type;
          }
        }
      }
      container actions {
        description
          "The actions that will be triggered if conditions are satisfied";
        list action {
          // NCS patched for predictable order
          ordered-by user;
          key "name type";
          leaf name {
            description
              "Name of the action";
            type string;
          }
          leaf type {
            description
              "Type of the action";
            type string;
          }
          uses property:ncs_template_property_list_definition;
          uses file_locators:ncs_template_file_locators_definition {
            status deprecated;
            description
              "Deprecated. Add a property named file_locator_name defined in the deployment.";
          }
        }
      }
    }
  }

  grouping ncs_rpc_notif_svc_dependency {
    container service_dependency {
      description
        "These are the services that needs to be running. Eg dns, syslog";
      list service {
        key "service_name service_version";
        leaf service_name {
          description
            "Dependent Service Name";
          type types:ncs_rpc_notif_escname;
          mandatory true;
        }
        leaf service_version {
          description
            "Version of the dependent service";
          type types:ncs_rpc_notif_escversion;
          mandatory true;
        }
      }
    }
  }

  grouping ncs_rpc_notif_net_dependency {
    container network_dependency {
      description
        "Existence of these networks are checked but are not created if it does
         not. If the dependency is not met, registration of the
         service fails. This is a list. One can specify as may network
         dependencies as required. For example, external or management
         network. These networks has to be pre-created and when
         specifying the interfaces, the network to which its has to be
         connected is specified.";
      leaf-list network {
        description
          "Name of the dependent networks";
        type types:ncs_rpc_notif_escnetname;
      }
    }
  }

  grouping ncs_rpc_notif_placement_group {
    list placement_group {
      description
        "Placement group. Specifying it as a list allows us to
         define mutual relationship among different combination of vm_groups.";
      key "name";
      leaf name {
        description
          "Name of placement group";
        type string;
        mandatory true;
      }
      leaf type {
        description
          "affinity or anti_affinity";
        type types:ncs_rpc_notif_placement_type;
        mandatory true;
      }
      leaf enforcement {
        description
          "Strict or Loose enforcement";
        type types:ncs_rpc_notif_enforcement;
        default "strict";
      }
      leaf-list vm_group {
        type leafref {
          path "../../../vm_group/name";
        }
        min-elements 1;
      }
    }
  }

  grouping ncs_rpc_notif_inter_vm_group_placement {
    list placement {
      description
        "Placement policy specification. Specifying it as a list allows us to
         define different placement policies among different
         combination of vm_groups";
      key "target_vm_group_ref type";
      leaf target_vm_group_ref {
        description
          "Name of the group whose VMs will be subjected to the placement
           rules specified below";
        type leafref {
          path "../../../vm_group/name";
        }
      }
      leaf type {
        description
          "affinity or anti_affinity";
        type types:ncs_rpc_notif_placement_type;
        mandatory true;
      }
      leaf enforcement {
        description
          "Strict or Loose enforcement";
        type types:ncs_rpc_notif_enforcement;
        default "strict";
      }
      leaf-list vm_group_ref {
        type leafref {
          path "../../../vm_group/name";
        }
        min-elements 1;
      }
    }
  }

  grouping ncs_rpc_notif_intra_vm_group_placement {
    list placement {
      description
        "Placement policy within a VM group. keying off of
         type as we cannot have same rule multiple times within
         the group.";
      key "type";
      leaf type {
        description
          "affinity, anti_affinity, zone_host";
        type types:ncs_rpc_notif_placement_type;
        mandatory true;
      }
      leaf enforcement {
        description
          "Strict or Loose enforcement";
        type types:ncs_rpc_notif_enforcement;
        default "strict";
      }
      choice zone_host {
        when "./type = 'zone_host'" {
          tailf:xpath-root 3;
        }
        case host {
          leaf host {
            description
              "Host on which the affinity rules specified above should be applied against the VMs of group specified above.";
            type types:ncs_rpc_notif_host_location_type;
            mandatory true;
          }
        }
        case zone {
          leaf zone {
            description
              "The availability zone in which the vm group will be deployed";
            type types:ncs_rpc_notif_escname;
            mandatory true;
          }
        }
      }
    }
  }

  grouping ncs_rpc_notif_recovery_policies {
    container recovery_policy {
      description
        "Policy of recovery";
      leaf recovery_type {
        description
          "The type of recovery";
        type types:ncs_rpc_notif_recovery_style_types;
        default "AUTO";
      }
      leaf action_on_recovery {
        description
          "The action performed during recovery";
        type types:ncs_rpc_notif_recovery_action_types;
        default "REBOOT_THEN_REDEPLOY";
      }
      leaf max_retries {
        description
          "The number of recovery attempts";
        type uint16;
      }
      leaf monitor_on_error {
        description
          "Continue monitoring of VM on error state.
           By Default monitoring is disabled on VM error state.
           When monitor_on_error flag is set to true, monitor is not disabled on error state and continues to monitor.";
        type boolean;
        default "false";
      }
    }
  }

  grouping ncs_rpc_notif_vmexport_policies {
    container vmexport_policy {
      description
        "Policy of vm export";
      list disk_exclusion {
        key "disk_name";
        leaf disk_name {
          description
            "The disk to exclude.  One of 'image name' /
             'image name:disk name' / 'volume name'";
          type string;
        }
      }
    }
  }

  grouping ncs_rpc_notif_intra_vm_group_properties {
    list shared_ip {
      description
        "Shared Ip is the ip address that is assigned to the vm_group";
      key "nicid";
      leaf nicid {
        description
          "Interface where the static_ip property is applied.
           Ensure that interface with this ID is specified earlier";
        type leafref {
          path "../../interfaces/interface/nicid";
        }
        mandatory true;
      }
      leaf static {
        description
          "Is the shared_ip static";
        type boolean;
        default "false";
      }
      leaf ip_address {
        description
          "Static IP address for this interface";
        type types:ncs_rpc_notif_escipaddr;
      }
    }
    container properties {
      description
        "List of key value pair to be passed to esc to
         configure the vmgroup properties. For example, key is NOTIFY_EXTERNAL_MONITOR
         and the value is ENABLED";
      list property {
        key "prop_key";
        leaf prop_key {
          description
            "key for the property";
          type types:ncs_rpc_notif_vm_group_properties;
        }
        leaf prop_value {
          description
            "value of the property";
          type types:ncs_rpc_notif_escbigdata;
        }
      }
    }
  }

  grouping ncs_rpc_notif_esc_policies {
    container policies {
      description
        "Describes different policies that can be specified that will affect
         the way VMs are brought up.";
      container external_dependencies {
        description
          "Any dependencies such as service dependencies or network dependencies
           are listed in this section. If the dependencies are not
           met, then registration is rejected. This is used to check
           for the existence of service or network but will not be
           created if the services or network is not present.";
        uses ncs_rpc_notif_svc_dependency;
        uses ncs_rpc_notif_net_dependency;
      }
      uses ncs_rpc_notif_placement_group;
      uses ncs_rpc_notif_inter_vm_group_placement;
      list startup {
        description
          "Start up sequence specification. This is achieved at the granularity
           of vm group. It allows one to specify start up of a
           particular group of VMs depends on which other groups. When
           do we say that the dependent group have successfully brought
           up ? This is achieved by waiting for an event that is
           specified. Can be collection of events too.";
        key "target_vm_group_ref";
        leaf target_vm_group_ref {
          description
            "Name of the group whose VMs will be subjected to the placement
             rules specified below";
          type leafref {
            path "../../../vm_group/name";
          }
        }
        list depends_on {
          key "vm_group_ref";
          leaf vm_group_ref {
            type leafref {
              path "../../../../vm_group/name";
            }
            mandatory true;
          }
          leaf-list kpi_event_ref {
            description
              "Here max and min elements is set to 1 as currently
               support only one event.";
            type leafref {
              path "../../../../vm_group[name = current()/../vm_group_ref]/kpi_data/kpi/event_name";
            }
            min-elements 1;
            max-elements 1;
          }
        }
      }
      uses ncs_rpc_notif_esc_policy;
    }
  }

  grouping ncs_rpc_notif_esc_policy {
    list policy {
      description
        "The policy list that contains a list of conditions and a list of actions";
      key "name";
      leaf name {
        description
          "Unique policy name";
        type string;
      }
      container conditions {
        description
          "The lifecycle stage conditions to trigger actions";
        list condition {
          key "name";
          leaf name {
            description
              "Unique condition type";
            type types:ncs_rpc_notif_policy_condition_type;
          }
        }
      }
      container actions {
        description
          "The actions that will be triggered if conditions are satisfied";
        list action {
          key "name type";
          leaf name {
            description
              "Name of the action";
            type string;
          }
          leaf type {
            description
              "Type of the action";
            type string;
          }
          uses property:ncs_rpc_notif_property_list_definition;
          uses file_locators:ncs_rpc_notif_file_locators_definition {
            status deprecated;
            description
              "Deprecated. Add a property named file_locator_name defined in the deployment.";
          }
        }
      }
    }
  }

  grouping live_ncs_svc_dependency {
    container service_dependency {
      description
        "These are the services that needs to be running. Eg dns, syslog";
      list service {
        key "service_name service_version";
        leaf service_name {
          description
            "Dependent Service Name";
          type types:live_ncs_escname;
          // NCS drop mandatory statement
        }
        leaf service_version {
          description
            "Version of the dependent service";
          type types:live_ncs_escversion;
          // NCS drop mandatory statement
        }
      }
    }
  }

  grouping live_ncs_net_dependency {
    container network_dependency {
      description
        "Existence of these networks are checked but are not created if it does
         not. If the dependency is not met, registration of the
         service fails. This is a list. One can specify as may network
         dependencies as required. For example, external or management
         network. These networks has to be pre-created and when
         specifying the interfaces, the network to which its has to be
         connected is specified.";
      leaf-list network {
        description
          "Name of the dependent networks";
        type types:live_ncs_escnetname;
      }
    }
  }

  grouping live_ncs_placement_group {
    list placement_group {
      description
        "Placement group. Specifying it as a list allows us to
         define mutual relationship among different combination of vm_groups.";
      key "name";
      leaf name {
        description
          "Name of placement group";
        type string;
        // NCS drop mandatory statement
      }
      leaf type {
        description
          "affinity or anti_affinity";
        type types:live_ncs_placement_type;
        // NCS drop mandatory statement
      }
      leaf enforcement {
        description
          "Strict or Loose enforcement";
        type types:live_ncs_enforcement;
        // NCS drop default statement
      }
      leaf-list vm_group {
        type leafref {
          path "../../../vm_group/name";
        }
        // NCS drop min-elements statement
      }
    }
  }

  grouping live_ncs_inter_vm_group_placement {
    list placement {
      description
        "Placement policy specification. Specifying it as a list allows us to
         define different placement policies among different
         combination of vm_groups";
      key "target_vm_group_ref type";
      leaf target_vm_group_ref {
        description
          "Name of the group whose VMs will be subjected to the placement
           rules specified below";
        type leafref {
          path "../../../vm_group/name";
        }
      }
      leaf type {
        description
          "affinity or anti_affinity";
        type types:live_ncs_placement_type;
        // NCS drop mandatory statement
      }
      leaf enforcement {
        description
          "Strict or Loose enforcement";
        type types:live_ncs_enforcement;
        // NCS drop default statement
      }
      leaf-list vm_group_ref {
        type leafref {
          path "../../../vm_group/name";
        }
        // NCS drop min-elements statement
      }
    }
  }

  grouping live_ncs_intra_vm_group_placement {
    list placement {
      description
        "Placement policy within a VM group. keying off of
         type as we cannot have same rule multiple times within
         the group.";
      key "type";
      leaf type {
        description
          "affinity, anti_affinity, zone_host";
        type types:live_ncs_placement_type;
        // NCS drop mandatory statement
      }
      leaf enforcement {
        description
          "Strict or Loose enforcement";
        type types:live_ncs_enforcement;
        // NCS drop default statement
      }
      choice zone_host {
        // NCS drop when statement
        case host {
          leaf host {
            description
              "Host on which the affinity rules specified above should be applied against the VMs of group specified above.";
            type types:live_ncs_host_location_type;
            // NCS drop mandatory statement
          }
        }
        case zone {
          leaf zone {
            description
              "The availability zone in which the vm group will be deployed";
            type types:live_ncs_escname;
            // NCS drop mandatory statement
          }
        }
      }
    }
  }

  grouping live_ncs_recovery_policies {
    container recovery_policy {
      description
        "Policy of recovery";
      leaf recovery_type {
        description
          "The type of recovery";
        type types:live_ncs_recovery_style_types;
        // NCS drop default statement
      }
      leaf action_on_recovery {
        description
          "The action performed during recovery";
        type types:live_ncs_recovery_action_types;
        // NCS drop default statement
      }
      leaf max_retries {
        description
          "The number of recovery attempts";
        type uint16;
      }
      leaf monitor_on_error {
        description
          "Continue monitoring of VM on error state.
           By Default monitoring is disabled on VM error state.
           When monitor_on_error flag is set to true, monitor is not disabled on error state and continues to monitor.";
        type boolean;
        // NCS drop default statement
      }
    }
  }

  grouping live_ncs_vmexport_policies {
    container vmexport_policy {
      description
        "Policy of vm export";
      list disk_exclusion {
        key "disk_name";
        leaf disk_name {
          description
            "The disk to exclude.  One of 'image name' /
             'image name:disk name' / 'volume name'";
          type string;
        }
      }
    }
  }

  grouping live_ncs_intra_vm_group_properties {
    list shared_ip {
      description
        "Shared Ip is the ip address that is assigned to the vm_group";
      key "nicid";
      leaf nicid {
        description
          "Interface where the static_ip property is applied.
           Ensure that interface with this ID is specified earlier";
        type leafref {
          path "../../interfaces/interface/nicid";
        }
        // NCS drop mandatory statement
      }
      leaf static {
        description
          "Is the shared_ip static";
        type boolean;
        // NCS drop default statement
      }
      leaf ip_address {
        description
          "Static IP address for this interface";
        type types:live_ncs_escipaddr;
      }
    }
    container properties {
      description
        "List of key value pair to be passed to esc to
         configure the vmgroup properties. For example, key is NOTIFY_EXTERNAL_MONITOR
         and the value is ENABLED";
      list property {
        key "prop_key";
        leaf prop_key {
          description
            "key for the property";
          type types:live_ncs_vm_group_properties;
        }
        leaf prop_value {
          description
            "value of the property";
          type types:live_ncs_escbigdata;
        }
      }
    }
  }

  grouping live_ncs_esc_policies {
    container policies {
      description
        "Describes different policies that can be specified that will affect
         the way VMs are brought up.";
      container external_dependencies {
        description
          "Any dependencies such as service dependencies or network dependencies
           are listed in this section. If the dependencies are not
           met, then registration is rejected. This is used to check
           for the existence of service or network but will not be
           created if the services or network is not present.";
        uses live_ncs_svc_dependency;
        uses live_ncs_net_dependency;
      }
      uses live_ncs_placement_group;
      uses live_ncs_inter_vm_group_placement;
      list startup {
        description
          "Start up sequence specification. This is achieved at the granularity
           of vm group. It allows one to specify start up of a
           particular group of VMs depends on which other groups. When
           do we say that the dependent group have successfully brought
           up ? This is achieved by waiting for an event that is
           specified. Can be collection of events too.";
        key "target_vm_group_ref";
        leaf target_vm_group_ref {
          description
            "Name of the group whose VMs will be subjected to the placement
             rules specified below";
          type leafref {
            path "../../../vm_group/name";
          }
        }
        list depends_on {
          key "vm_group_ref";
          leaf vm_group_ref {
            type leafref {
              path "../../../../vm_group/name";
            }
            // NCS drop mandatory statement
          }
          leaf-list kpi_event_ref {
            description
              "Here max and min elements is set to 1 as currently
               support only one event.";
            type leafref {
              path "../../../../vm_group[name = current()/../vm_group_ref]/kpi_data/kpi/event_name";
            }
            // NCS drop min-elements statement
            // NCS drop max-elements statement
          }
        }
      }
      uses live_ncs_esc_policy;
    }
  }

  grouping live_ncs_esc_policy {
    list policy {
      description
        "The policy list that contains a list of conditions and a list of actions";
      key "name";
      leaf name {
        description
          "Unique policy name";
        type string;
      }
      container conditions {
        description
          "The lifecycle stage conditions to trigger actions";
        list condition {
          key "name";
          leaf name {
            description
              "Unique condition type";
            type types:live_ncs_policy_condition_type;
          }
        }
      }
      container actions {
        description
          "The actions that will be triggered if conditions are satisfied";
        list action {
          key "name type";
          leaf name {
            description
              "Name of the action";
            type string;
          }
          leaf type {
            description
              "Type of the action";
            type string;
          }
          uses property:live_ncs_property_list_definition;
          uses file_locators:live_ncs_file_locators_definition {
            status deprecated;
            description
              "Deprecated. Add a property named file_locator_name defined in the deployment.";
          }
        }
      }
    }
  }

  grouping svc_dependency {
    container service_dependency {
      description
        "These are the services that needs to be running. Eg dns, syslog";
      list service {
        key "service_name service_version";
        leaf service_name {
          description
            "Dependent Service Name";
          type types:escname;
          mandatory true;
        }
        leaf service_version {
          description
            "Version of the dependent service";
          type types:escversion;
          mandatory true;
        }
      }
    }
  }

  grouping net_dependency {
    container network_dependency {
      description
        "Existence of these networks are checked but are not created if it does
         not. If the dependency is not met, registration of the
         service fails. This is a list. One can specify as may network
         dependencies as required. For example, external or management
         network. These networks has to be pre-created and when
         specifying the interfaces, the network to which its has to be
         connected is specified.";
      leaf-list network {
        description
          "Name of the dependent networks";
        type types:escnetname;
      }
    }
  }

  grouping placement_group {
    list placement_group {
      description
        "Placement group. Specifying it as a list allows us to
         define mutual relationship among different combination of vm_groups.";
      key "name";
      leaf name {
        description
          "Name of placement group";
        type string;
        mandatory true;
      }
      leaf type {
        description
          "affinity or anti_affinity";
        type types:placement_type;
        mandatory true;
      }
      leaf enforcement {
        description
          "Strict or Loose enforcement";
        type types:enforcement;
        default "strict";
      }
      leaf-list vm_group {
        type leafref {
          path "../../../vm_group/name";
        }
        min-elements 1;
      }
    }
  }

  grouping inter_vm_group_placement {
    list placement {
      description
        "Placement policy specification. Specifying it as a list allows us to
         define different placement policies among different
         combination of vm_groups";
      key "target_vm_group_ref type";
      leaf target_vm_group_ref {
        description
          "Name of the group whose VMs will be subjected to the placement
           rules specified below";
        type leafref {
          path "../../../vm_group/name";
        }
      }
      leaf type {
        description
          "affinity or anti_affinity";
        type types:placement_type;
        mandatory true;
      }
      leaf enforcement {
        description
          "Strict or Loose enforcement";
        type types:enforcement;
        default "strict";
      }
      leaf-list vm_group_ref {
        type leafref {
          path "../../../vm_group/name";
        }
        min-elements 1;
      }
    }
  }

  grouping intra_vm_group_placement {
    list placement {
      description
        "Placement policy within a VM group. keying off of
         type as we cannot have same rule multiple times within
         the group.";
      key "type";
      leaf type {
        description
          "affinity, anti_affinity, zone_host";
        type types:placement_type;
        mandatory true;
      }
      leaf enforcement {
        description
          "Strict or Loose enforcement";
        type types:enforcement;
        default "strict";
      }
      choice zone_host {
        when "./type = 'zone_host'" {
          tailf:xpath-root 3;
        }
        case host {
          leaf host {
            description
              "Host on which the affinity rules specified above should be applied against the VMs of group specified above.";
            type types:host_location_type;
            mandatory true;
          }
        }
        case zone {
          leaf zone {
            description
              "The availability zone in which the vm group will be deployed";
            type types:escname;
            mandatory true;
          }
        }
      }
    }
  }

  grouping recovery_policies {
    container recovery_policy {
      description
        "Policy of recovery";
      leaf recovery_type {
        description
          "The type of recovery";
        type types:recovery_style_types;
        default "AUTO";
      }
      leaf action_on_recovery {
        description
          "The action performed during recovery";
        type types:recovery_action_types;
        default "REBOOT_THEN_REDEPLOY";
      }
      leaf max_retries {
        description
          "The number of recovery attempts";
        type uint16;
      }
      leaf monitor_on_error {
        description
          "Continue monitoring of VM on error state.
           By Default monitoring is disabled on VM error state.
           When monitor_on_error flag is set to true, monitor is not disabled on error state and continues to monitor.";
        type boolean;
        default "false";
      }
    }
  }

  grouping vmexport_policies {
    container vmexport_policy {
      description
        "Policy of vm export";
      list disk_exclusion {
        key "disk_name";
        leaf disk_name {
          description
            "The disk to exclude.  One of 'image name' /
             'image name:disk name' / 'volume name'";
          type string;
        }
      }
    }
  }

  grouping intra_vm_group_properties {
    list shared_ip {
      description
        "Shared Ip is the ip address that is assigned to the vm_group";
      key "nicid";
      leaf nicid {
        description
          "Interface where the static_ip property is applied.
           Ensure that interface with this ID is specified earlier";
        type leafref {
          path "../../interfaces/interface/nicid";
        }
        mandatory true;
      }
      leaf static {
        description
          "Is the shared_ip static";
        type boolean;
        default "false";
      }
      leaf ip_address {
        description
          "Static IP address for this interface";
        type types:escipaddr;
      }
    }
    container properties {
      description
        "List of key value pair to be passed to esc to
         configure the vmgroup properties. For example, key is NOTIFY_EXTERNAL_MONITOR
         and the value is ENABLED";
      list property {
        key "prop_key";
        leaf prop_key {
          description
            "key for the property";
          type types:vm_group_properties;
        }
        leaf prop_value {
          description
            "value of the property";
          type types:escbigdata;
        }
      }
    }
  }

  grouping esc_policies {
    container policies {
      description
        "Describes different policies that can be specified that will affect
         the way VMs are brought up.";
      container external_dependencies {
        description
          "Any dependencies such as service dependencies or network dependencies
           are listed in this section. If the dependencies are not
           met, then registration is rejected. This is used to check
           for the existence of service or network but will not be
           created if the services or network is not present.";
        uses svc_dependency;
        uses net_dependency;
      }
      uses placement_group;
      uses inter_vm_group_placement;
      list startup {
        description
          "Start up sequence specification. This is achieved at the granularity
           of vm group. It allows one to specify start up of a
           particular group of VMs depends on which other groups. When
           do we say that the dependent group have successfully brought
           up ? This is achieved by waiting for an event that is
           specified. Can be collection of events too.";
        key "target_vm_group_ref";
        leaf target_vm_group_ref {
          description
            "Name of the group whose VMs will be subjected to the placement
             rules specified below";
          type leafref {
            path "../../../vm_group/name";
          }
        }
        list depends_on {
          key "vm_group_ref";
          leaf vm_group_ref {
            type leafref {
              path "../../../../vm_group/name";
            }
            mandatory true;
          }
          leaf-list kpi_event_ref {
            description
              "Here max and min elements is set to 1 as currently
               support only one event.";
            type leafref {
              path "../../../../vm_group[name = current()/../vm_group_ref]/kpi_data/kpi/event_name";
            }
            min-elements 1;
            max-elements 1;
          }
        }
      }
      uses esc_policy;
    }
  }

  grouping esc_policy {
    list policy {
      description
        "The policy list that contains a list of conditions and a list of actions";
      key "name";
      leaf name {
        description
          "Unique policy name";
        type string;
      }
      container conditions {
        description
          "The lifecycle stage conditions to trigger actions";
        list condition {
          key "name";
          leaf name {
            description
              "Unique condition type";
            type types:policy_condition_type;
          }
        }
      }
      container actions {
        description
          "The actions that will be triggered if conditions are satisfied";
        list action {
          key "name type";
          leaf name {
            description
              "Name of the action";
            type string;
          }
          leaf type {
            description
              "Type of the action";
            type string;
          }
          uses property:property_list_definition;
          uses file_locators:file_locators_definition {
            status deprecated;
            description
              "Deprecated. Add a property named file_locator_name defined in the deployment.";
          }
        }
      }
    }
  }
}
