module esc_opdata_flavors {
  // Generated by yanger -t ncs
  tailf:mount-id esc-nc-1.0:esc-nc-1.0;
  tailf:ncs-device-type "netconf";

  namespace "http://www.cisco.com/esc/esc_opdata_flavors";
  prefix esc_opdata_flavors;

  import ietf-yang-types {
    prefix ietf-yang-types;
  }
  import esc_opdata_flavor_state_machine {
    prefix opstatemachines;
  }
  import "esc-nc-1.0" {
    prefix "esc-nc-1.0";
  }
  import tailf-ncs {
    prefix ncs;
  }
  import tailf-common {
    prefix tailf;
  }

  organization
    "Cisco Systems";
  contact
    "Natasha Shrestha <nashrest@cisco.com>";

  revision 2015-07-06 {
    description
      "Elastic Services Controller Module's flavors' operational data";
  }

  grouping ncs_template_esc_opdata_flavors {
    description
      "This contains all the operational data of the flavors";
    container flavors {
      list flavor {
        // NCS patched for predictable order
        ordered-by user;
        description
          "Flavor running information";
        key "name";
        leaf name {
          description
            "Name of the flavor";
          type string;
        }
        leaf flavor_id {
          description
            "ID of the flavor";
          type string;
        }
        leaf public {
          description
            "True if the flavor is public";
          type string;
          // NCS drop default statement
        }
        uses opstatemachines:ncs_template_esc_opdata_flavor_state_machine;
      }
    }
  }

  grouping ncs_rpc_notif_esc_opdata_flavors {
    description
      "This contains all the operational data of the flavors";
    container flavors {
      list flavor {
        description
          "Flavor running information";
        key "name";
        leaf name {
          description
            "Name of the flavor";
          type string;
        }
        leaf flavor_id {
          description
            "ID of the flavor";
          type ietf-yang-types:uuid;
        }
        leaf public {
          description
            "True if the flavor is public";
          type boolean;
          default "true";
        }
        uses opstatemachines:ncs_rpc_notif_esc_opdata_flavor_state_machine;
      }
    }
  }

  grouping live_ncs_esc_opdata_flavors {
    description
      "This contains all the operational data of the flavors";
    container flavors {
      list flavor {
        description
          "Flavor running information";
        key "name";
        leaf name {
          description
            "Name of the flavor";
          type string;
        }
        leaf flavor_id {
          description
            "ID of the flavor";
          type ietf-yang-types:uuid;
        }
        leaf public {
          description
            "True if the flavor is public";
          type boolean;
          // NCS drop default statement
        }
        uses opstatemachines:live_ncs_esc_opdata_flavor_state_machine;
      }
    }
  }

  grouping esc_opdata_flavors {
    description
      "This contains all the operational data of the flavors";
    container flavors {
      list flavor {
        description
          "Flavor running information";
        key "name";
        leaf name {
          description
            "Name of the flavor";
          type string;
        }
        leaf flavor_id {
          description
            "ID of the flavor";
          type ietf-yang-types:uuid;
        }
        leaf public {
          description
            "True if the flavor is public";
          type boolean;
          default "true";
        }
        uses opstatemachines:esc_opdata_flavor_state_machine;
      }
    }
  }
}
