module esc_container_services {
  // Generated by yanger -t ncs
  tailf:mount-id esc-nc-1.0:esc-nc-1.0;
  tailf:ncs-device-type "netconf";

  namespace "http://www.cisco.com/esc/esc_containers";
  prefix esc_containers;

  import esc_types {
    prefix types;
  }
  import "esc-nc-1.0" {
    prefix "esc-nc-1.0";
  }
  import tailf-ncs {
    prefix ncs;
  }
  import tailf-common {
    prefix tailf;
  }

  organization
    "Cisco Systems";
  contact
    "ESC Team <esc-support@cisco.com>";
  description
    "K8S container support provided by ESC. The intent is
        to define a set of data structures that will enable us to support
        the following container orchestration solutions";

  revision 2019-10-22 {
    description
      "Datamodel support for K8S containers";
  }

  grouping ncs_template_services {
    description
      "Container Service Configuration";
    container services {
      description
        "Declaration of services defined for container services";
      list service {
        // NCS patched for predictable order
        ordered-by user;
        description
          "List of virtual services";
        key "name";
        leaf name {
          description
            "Name of the virtual service";
          type types:ncs_template_escname;
          // NCS drop mandatory statement
        }
        leaf type {
          description
            "Type of service";
          type types:ncs_template_service_type;
          // NCS drop mandatory statement
        }
        container ports {
          list port {
            // NCS patched for predictable order
            ordered-by user;
            description
              "List of virtual ports";
            key "internal_port";
            leaf internal_port {
              description
                "The internal port for this service";
              type string;
              // NCS drop mandatory statement
            }
            leaf protocol {
              description
                "The protocol for this service";
              type types:ncs_template_ipprotocol_t;
              // NCS drop mandatory statement
            }
            leaf external_port {
              description
                "The external port for this service";
              type string;
              // NCS drop mandatory statement
            }
          }
        }
        container selector {
          choice selectors {
            case cidr {
              leaf cidr {
                description
                  "Classless Inter Domain Routing address";
                type string;
              }
            }
            case label {
              leaf vm_group {
                description
                  "VM Group selector";
                type string;
              }
              leaf nicid {
                description
                  "Interface NIC";
                type string;
              }
            }
          }
        }
      }
    }
  }

  grouping ncs_rpc_notif_services {
    description
      "Container Service Configuration";
    container services {
      description
        "Declaration of services defined for container services";
      list service {
        description
          "List of virtual services";
        key "name";
        leaf name {
          description
            "Name of the virtual service";
          type types:ncs_rpc_notif_escname;
          mandatory true;
        }
        leaf type {
          description
            "Type of service";
          type types:ncs_rpc_notif_service_type;
          mandatory true;
        }
        container ports {
          list port {
            description
              "List of virtual ports";
            key "internal_port";
            leaf internal_port {
              description
                "The internal port for this service";
              type uint16;
              mandatory true;
            }
            leaf protocol {
              description
                "The protocol for this service";
              type types:ncs_rpc_notif_ipprotocol_t;
              mandatory false;
            }
            leaf external_port {
              description
                "The external port for this service";
              type uint16;
              mandatory false;
            }
          }
        }
        container selector {
          choice selectors {
            case cidr {
              leaf cidr {
                description
                  "Classless Inter Domain Routing address";
                type string;
              }
            }
            case label {
              leaf vm_group {
                description
                  "VM Group selector";
                type string;
              }
              leaf nicid {
                description
                  "Interface NIC";
                type uint16;
              }
            }
          }
        }
      }
    }
  }

  grouping live_ncs_services {
    description
      "Container Service Configuration";
    container services {
      description
        "Declaration of services defined for container services";
      list service {
        description
          "List of virtual services";
        key "name";
        leaf name {
          description
            "Name of the virtual service";
          type types:live_ncs_escname;
          // NCS drop mandatory statement
        }
        leaf type {
          description
            "Type of service";
          type types:live_ncs_service_type;
          // NCS drop mandatory statement
        }
        container ports {
          list port {
            description
              "List of virtual ports";
            key "internal_port";
            leaf internal_port {
              description
                "The internal port for this service";
              type uint16;
              // NCS drop mandatory statement
            }
            leaf protocol {
              description
                "The protocol for this service";
              type types:live_ncs_ipprotocol_t;
              // NCS drop mandatory statement
            }
            leaf external_port {
              description
                "The external port for this service";
              type uint16;
              // NCS drop mandatory statement
            }
          }
        }
        container selector {
          choice selectors {
            case cidr {
              leaf cidr {
                description
                  "Classless Inter Domain Routing address";
                type string;
              }
            }
            case label {
              leaf vm_group {
                description
                  "VM Group selector";
                type string;
              }
              leaf nicid {
                description
                  "Interface NIC";
                type uint16;
              }
            }
          }
        }
      }
    }
  }

  grouping services {
    description
      "Container Service Configuration";
    container services {
      description
        "Declaration of services defined for container services";
      list service {
        description
          "List of virtual services";
        key "name";
        leaf name {
          description
            "Name of the virtual service";
          type types:escname;
          mandatory true;
        }
        leaf type {
          description
            "Type of service";
          type types:service_type;
          mandatory true;
        }
        container ports {
          list port {
            description
              "List of virtual ports";
            key "internal_port";
            leaf internal_port {
              description
                "The internal port for this service";
              type uint16;
              mandatory true;
            }
            leaf protocol {
              description
                "The protocol for this service";
              type types:ipprotocol_t;
              mandatory false;
            }
            leaf external_port {
              description
                "The external port for this service";
              type uint16;
              mandatory false;
            }
          }
        }
        container selector {
          choice selectors {
            case cidr {
              leaf cidr {
                description
                  "Classless Inter Domain Routing address";
                type string;
              }
            }
            case label {
              leaf vm_group {
                description
                  "VM Group selector";
                type string;
              }
              leaf nicid {
                description
                  "Interface NIC";
                type uint16;
              }
            }
          }
        }
      }
    }
  }
}
