module esc_info {
  // Generated by yanger -t ncs
  tailf:mount-id esc-nc-1.0:esc-nc-1.0;
  tailf:ncs-device-type "netconf";

  namespace "http://www.cisco.com/esc/esc_info";
  prefix esc_info;

  import "esc-nc-1.0" {
    prefix "esc-nc-1.0";
  }
  import tailf-ncs {
    prefix ncs;
  }
  import tailf-common {
    prefix tailf;
  }

  organization
    "Cisco Systems";
  contact
    "Steve Zhu <hezh@cisco.com>";

  revision 2015-06-05 {
    description
      "Added info container";
  }
  revision 2014-08-06 {
    description
      "Elastic Services Controller Module's operational data";
  }

  grouping ncs_template_esc_info {
    leaf product_name {
      description
        "Official name of ESC";
      type string;
      // NCS drop default statement
    }
    container esc_version {
      description
        "Version of current ESC load";
      leaf major {
        description
          "Major version";
        type string;
        // NCS drop default statement
      }
      leaf minor {
        description
          "Minor version";
        type string;
        // NCS drop default statement
      }
      leaf sprint {
        description
          "Sprint number";
        type string;
        // NCS drop default statement
      }
      leaf release {
        description
          "Build number";
        type string;
        // NCS drop default statement
      }
      leaf yang_model {
        description
          "Version of YANG data model";
        type string;
        // NCS drop default statement
      }
      leaf timestamp {
        description
          "Build timestamp";
        type string;
        // NCS drop default statement
      }
    }
    container copyright {
      description
        "ESC copyright info";
      leaf company {
        description
          "Company who owns ESC";
        type string;
        // NCS drop default statement
      }
      leaf homepage {
        description
          "ESC homepage";
        type string;
        // NCS drop default statement
      }
    }
  }

  grouping ncs_rpc_notif_esc_info {
    leaf product_name {
      description
        "Official name of ESC";
      type string;
      default "Elastic Services Controller";
    }
    container esc_version {
      description
        "Version of current ESC load";
      leaf major {
        description
          "Major version";
        type string;
        default "Unknown";
      }
      leaf minor {
        description
          "Minor version";
        type string;
        default "Unknown";
      }
      leaf sprint {
        description
          "Sprint number";
        type string;
        default "Unknown";
      }
      leaf release {
        description
          "Build number";
        type string;
        default "Unknown";
      }
      leaf yang_model {
        description
          "Version of YANG data model";
        type string;
        default "Unknown";
      }
      leaf timestamp {
        description
          "Build timestamp";
        type string;
        default "Unknown";
      }
    }
    container copyright {
      description
        "ESC copyright info";
      leaf company {
        description
          "Company who owns ESC";
        type string;
        default "Cisco Systems";
      }
      leaf homepage {
        description
          "ESC homepage";
        type string;
        default "http://www.cisco.com/c/en/us/support/cloud-systems-management/elastic-services-controller-esc/tsd-products-support-series-home.html";
      }
    }
  }

  grouping live_ncs_esc_info {
    leaf product_name {
      description
        "Official name of ESC";
      type string;
      // NCS drop default statement
    }
    container esc_version {
      description
        "Version of current ESC load";
      leaf major {
        description
          "Major version";
        type string;
        // NCS drop default statement
      }
      leaf minor {
        description
          "Minor version";
        type string;
        // NCS drop default statement
      }
      leaf sprint {
        description
          "Sprint number";
        type string;
        // NCS drop default statement
      }
      leaf release {
        description
          "Build number";
        type string;
        // NCS drop default statement
      }
      leaf yang_model {
        description
          "Version of YANG data model";
        type string;
        // NCS drop default statement
      }
      leaf timestamp {
        description
          "Build timestamp";
        type string;
        // NCS drop default statement
      }
    }
    container copyright {
      description
        "ESC copyright info";
      leaf company {
        description
          "Company who owns ESC";
        type string;
        // NCS drop default statement
      }
      leaf homepage {
        description
          "ESC homepage";
        type string;
        // NCS drop default statement
      }
    }
  }

  grouping esc_info {
    leaf product_name {
      description
        "Official name of ESC";
      type string;
      default "Elastic Services Controller";
    }
    container esc_version {
      description
        "Version of current ESC load";
      leaf major {
        description
          "Major version";
        type string;
        default "Unknown";
      }
      leaf minor {
        description
          "Minor version";
        type string;
        default "Unknown";
      }
      leaf sprint {
        description
          "Sprint number";
        type string;
        default "Unknown";
      }
      leaf release {
        description
          "Build number";
        type string;
        default "Unknown";
      }
      leaf yang_model {
        description
          "Version of YANG data model";
        type string;
        default "Unknown";
      }
      leaf timestamp {
        description
          "Build timestamp";
        type string;
        default "Unknown";
      }
    }
    container copyright {
      description
        "ESC copyright info";
      leaf company {
        description
          "Company who owns ESC";
        type string;
        default "Cisco Systems";
      }
      leaf homepage {
        description
          "ESC homepage";
        type string;
        default "http://www.cisco.com/c/en/us/support/cloud-systems-management/elastic-services-controller-esc/tsd-products-support-series-home.html";
      }
    }
  }
}
