module esc_rules {
  // Generated by yanger -t ncs
  tailf:mount-id esc-nc-1.0:esc-nc-1.0;
  tailf:ncs-device-type "netconf";

  namespace "http://www.cisco.com/esc/esc_rules";
  prefix esc_rules;

  import esc_property {
    prefix property;
  }
  import esc_types {
    prefix types;
  }
  import "esc-nc-1.0" {
    prefix "esc-nc-1.0";
  }
  import tailf-ncs {
    prefix ncs;
  }
  import tailf-common {
    prefix tailf;
  }

  organization
    "Cisco Systems";
  contact
    "Shesha Sreenivasamurthy <shesha@cisco.com>";
  description
    "ESC's rules descriptions'";

  revision 2014-06-23 {
    description
      "ESC Rules";
  }

  grouping ncs_template_kpi_rules {
    description
      "Actions that should be taken by ESC or by some other module on behalf
       of ESC when an event is triggered by the event
       generator. Every rule will have a name and an action script
       associated with it. The action script is a URL from where ESC
       downloads the script and executes when and event corresponding
       to the 'event_name' is triggered.";
    list rule {
      // NCS patched for predictable order
      ordered-by user;
      key "event_name";
      leaf event_name {
        description
          "Event name: Corresponding event_name should be present in the
           monitoring section";
        type string;
        // NCS drop mandatory statement
      }
      leaf-list action {
        // NCS patched for predictable order
        ordered-by user;
        description
          "Action associated with the above event.
           There is a specific format for
           this and the description should be updated with more useful
           information.";
        type string;
      }
      uses property:ncs_template_property_list_definition;
    }
  }

  grouping ncs_template_esc_rules {
    container rules {
      container admin_rules {
        description
          "These are the rules that an administrator specifies when the service
           is registered. This action is taken for each and every
           deployment of the service.";
        uses ncs_template_kpi_rules;
      }
      container user_rules {
        description
          "These are user specified rules which are an addendum for the admin
           rules. These are per deployment. For example: User may want
           to know when his VM died. The script may just generate an
           Email";
        uses ncs_template_kpi_rules;
      }
    }
  }

  grouping ncs_template_lcm_rules {
    description
      "The Life-Cycle-Management Rules define actions that need to take place
       at a certain stage of the VM or Service's life cycle";
    container lcm_rules {
      list lcm_rule {
        // NCS patched for predictable order
        ordered-by user;
        key "lifecycle_stage";
        leaf lifecycle_stage {
          description
            "Defines the stage at which this action(s) need to be executed.";
          type types:ncs_template_life_cycle_stage_type;
        }
        container actions {
          list action {
            // NCS patched for predictable order
            ordered-by user;
            key "name";
            leaf name {
              description
                "Name of the action.";
              type string;
            }
            leaf type {
              description
                "Type of the action";
              type string;
              // NCS drop mandatory statement
            }
            leaf stop_on_error {
              description
                "If true, stops VM/Service life cycle if action
                 throws an error.";
              type string;
              // NCS drop mandatory statement
            }
            uses property:ncs_template_property_list_definition;
          }
        }
      }
    }
  }

  grouping ncs_rpc_notif_kpi_rules {
    description
      "Actions that should be taken by ESC or by some other module on behalf
       of ESC when an event is triggered by the event
       generator. Every rule will have a name and an action script
       associated with it. The action script is a URL from where ESC
       downloads the script and executes when and event corresponding
       to the 'event_name' is triggered.";
    list rule {
      key "event_name";
      leaf event_name {
        description
          "Event name: Corresponding event_name should be present in the
           monitoring section";
        type leafref {
          path "../../../../kpi_data/kpi/event_name";
        }
        mandatory true;
      }
      leaf-list action {
        description
          "Action associated with the above event.
           There is a specific format for
           this and the description should be updated with more useful
           information.";
        type string;
      }
      uses property:ncs_rpc_notif_property_list_definition;
    }
  }

  grouping ncs_rpc_notif_esc_rules {
    container rules {
      container admin_rules {
        description
          "These are the rules that an administrator specifies when the service
           is registered. This action is taken for each and every
           deployment of the service.";
        uses ncs_rpc_notif_kpi_rules;
      }
      container user_rules {
        description
          "These are user specified rules which are an addendum for the admin
           rules. These are per deployment. For example: User may want
           to know when his VM died. The script may just generate an
           Email";
        uses ncs_rpc_notif_kpi_rules;
      }
    }
  }

  grouping ncs_rpc_notif_lcm_rules {
    description
      "The Life-Cycle-Management Rules define actions that need to take place
       at a certain stage of the VM or Service's life cycle";
    container lcm_rules {
      list lcm_rule {
        key "lifecycle_stage";
        leaf lifecycle_stage {
          description
            "Defines the stage at which this action(s) need to be executed.";
          type types:ncs_rpc_notif_life_cycle_stage_type;
        }
        container actions {
          list action {
            key "name";
            leaf name {
              description
                "Name of the action.";
              type string;
            }
            leaf type {
              description
                "Type of the action";
              type string;
              mandatory true;
            }
            leaf stop_on_error {
              description
                "If true, stops VM/Service life cycle if action
                 throws an error.";
              type boolean;
              mandatory true;
            }
            uses property:ncs_rpc_notif_property_list_definition;
          }
        }
      }
    }
  }

  grouping live_ncs_kpi_rules {
    description
      "Actions that should be taken by ESC or by some other module on behalf
       of ESC when an event is triggered by the event
       generator. Every rule will have a name and an action script
       associated with it. The action script is a URL from where ESC
       downloads the script and executes when and event corresponding
       to the 'event_name' is triggered.";
    list rule {
      key "event_name";
      leaf event_name {
        description
          "Event name: Corresponding event_name should be present in the
           monitoring section";
        type leafref {
          path "../../../../kpi_data/kpi/event_name";
        }
        // NCS drop mandatory statement
      }
      leaf-list action {
        description
          "Action associated with the above event.
           There is a specific format for
           this and the description should be updated with more useful
           information.";
        type string;
      }
      uses property:live_ncs_property_list_definition;
    }
  }

  grouping live_ncs_esc_rules {
    container rules {
      container admin_rules {
        description
          "These are the rules that an administrator specifies when the service
           is registered. This action is taken for each and every
           deployment of the service.";
        uses live_ncs_kpi_rules;
      }
      container user_rules {
        description
          "These are user specified rules which are an addendum for the admin
           rules. These are per deployment. For example: User may want
           to know when his VM died. The script may just generate an
           Email";
        uses live_ncs_kpi_rules;
      }
    }
  }

  grouping live_ncs_lcm_rules {
    description
      "The Life-Cycle-Management Rules define actions that need to take place
       at a certain stage of the VM or Service's life cycle";
    container lcm_rules {
      list lcm_rule {
        key "lifecycle_stage";
        leaf lifecycle_stage {
          description
            "Defines the stage at which this action(s) need to be executed.";
          type types:live_ncs_life_cycle_stage_type;
        }
        container actions {
          list action {
            key "name";
            leaf name {
              description
                "Name of the action.";
              type string;
            }
            leaf type {
              description
                "Type of the action";
              type string;
              // NCS drop mandatory statement
            }
            leaf stop_on_error {
              description
                "If true, stops VM/Service life cycle if action
                 throws an error.";
              type boolean;
              // NCS drop mandatory statement
            }
            uses property:live_ncs_property_list_definition;
          }
        }
      }
    }
  }

  grouping kpi_rules {
    description
      "Actions that should be taken by ESC or by some other module on behalf
       of ESC when an event is triggered by the event
       generator. Every rule will have a name and an action script
       associated with it. The action script is a URL from where ESC
       downloads the script and executes when and event corresponding
       to the 'event_name' is triggered.";
    list rule {
      key "event_name";
      leaf event_name {
        description
          "Event name: Corresponding event_name should be present in the
           monitoring section";
        type leafref {
          path "../../../../kpi_data/kpi/event_name";
        }
        mandatory true;
      }
      leaf-list action {
        description
          "Action associated with the above event.
           There is a specific format for
           this and the description should be updated with more useful
           information.";
        type string;
      }
      uses property:property_list_definition;
    }
  }

  grouping esc_rules {
    container rules {
      container admin_rules {
        description
          "These are the rules that an administrator specifies when the service
           is registered. This action is taken for each and every
           deployment of the service.";
        uses kpi_rules;
      }
      container user_rules {
        description
          "These are user specified rules which are an addendum for the admin
           rules. These are per deployment. For example: User may want
           to know when his VM died. The script may just generate an
           Email";
        uses kpi_rules;
      }
    }
  }

  grouping lcm_rules {
    description
      "The Life-Cycle-Management Rules define actions that need to take place
       at a certain stage of the VM or Service's life cycle";
    container lcm_rules {
      list lcm_rule {
        key "lifecycle_stage";
        leaf lifecycle_stage {
          description
            "Defines the stage at which this action(s) need to be executed.";
          type types:life_cycle_stage_type;
        }
        container actions {
          list action {
            key "name";
            leaf name {
              description
                "Name of the action.";
              type string;
            }
            leaf type {
              description
                "Type of the action";
              type string;
              mandatory true;
            }
            leaf stop_on_error {
              description
                "If true, stops VM/Service life cycle if action
                 throws an error.";
              type boolean;
              mandatory true;
            }
            uses property:property_list_definition;
          }
        }
      }
    }
  }
}
