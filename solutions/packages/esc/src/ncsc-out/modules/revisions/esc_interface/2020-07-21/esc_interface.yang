module esc_interface {
  // Generated by yanger -t ncs
  tailf:mount-id esc-nc-1.0:esc-nc-1.0;
  tailf:ncs-device-type "netconf";

  namespace "http://www.cisco.com/esc/esc_interface";
  prefix esc_interface;

  import esc_types {
    prefix types;
  }
  import esc_port_forwarding {
    prefix port_forwarding;
  }
  import "esc-nc-1.0" {
    prefix "esc-nc-1.0";
  }
  import tailf-ncs {
    prefix ncs;
  }
  import tailf-common {
    prefix tailf;
  }

  organization
    "Cisco Systems";
  contact
    "Shesha Sreenivasamurthy <shesha@cisco.com>";
  description
    "ESC's interface descriptions'";

  revision 2020-07-21 {
    description
      "Remove default value for admin_state_up";
  }
  revision 2020-06-18 {
    description
      "Adding admin_state_up to interface";
  }
  revision 2020-02-13 {
    description
      "Adding binding_profile to interface";
  }
  revision 2019-05-24 {
    description
      "Changed validation for ip_address within address list, requires scaling pool";
  }
  revision 2018-03-28 {
    description
      "Added address_id to address list and renamed address_info to address";
  }
  revision 2018-03-05 {
    description
      "Added public_ip_address within interface";
  }
  revision 2018-03-02 {
    description
      "Added interface_multi_address for supporting multiple subnets";
  }
  revision 2017-12-19 {
    description
      "Added validation for mac_address within esc_interface_details, requires scaling pool.";
  }
  revision 2017-12-03 {
    description
      "Added validation for ip_address within esc_interface_details, requires scaling pool.";
  }
  revision 2017-11-01 {
    description
      "Added port_security_enabled within interface";
  }
  revision 2017-08-04 {
    description
      "Added vim_interface_name within interface";
  }
  revision 2017-03-20 {
    description
      "Added support for prefix length on subnet address in allowed_address_pair";
  }
  revision 2017-02-01 {
    description
      "Add a choice for interface list. Interface now can also refer to an existing port.";
  }
  revision 2015-10-23 {
    description
      "Add security_groups container for security_group leaf-list within interface";
  }
  revision 2015-10-22 {
    description
      "Add security_group leaf within interface";
  }
  revision 2015-08-21 {
    description
      "Add subnet leaf within interface";
  }
  revision 2015-07-20 {
    description
      "In interface list removed the must condition on nicid";
  }
  revision 2015-06-09 {
    description
      "added allowed_address_pair support for ip and network list";
  }
  revision 2015-06-08 {
    description
      "added esc_port_forwarding";
  }
  revision 2015-06-04 {
    description
      "updated description";
  }
  revision 2014-06-23 {
    description
      "ESC Interface";
  }

  grouping ncs_template_esc_interface_addresses {
    container addresses {
      list address {
        // NCS patched for predictable order
        ordered-by user;
        key "address_id";
        leaf address_id {
          description
            "Id for the address in address list.";
          type string;
          // NCS drop mandatory statement
        }
        leaf subnet {
          description
            "Subnet name or uuid for allocating IP to this port";
          type types:ncs_template_escnetname;
        }
        leaf ip_address {
          description
            "Static IP address for this specific subnet";
          type types:ncs_template_escipaddr;
          // NCS drop must statement
        }
      }
    }
  }

  grouping ncs_template_esc_interface_details {
    leaf type {
      description
        "Interface Type: virtual/passthru";
      type types:ncs_template_iface_type;
      // NCS drop default statement
    }
    leaf vim_interface_name {
      description
        "User specified name for the interface on the VIM";
      type types:ncs_template_escname;
    }
    leaf model {
      description
        "In case of virtual: e1000 or virtio. In case of passthrough:
         Model of the NIC. This will be specific to the data center. Data
         centers may have NICs that support virtual functions from
         different vendors, like Intel, Cisco etc. Passthrough is
         not currently supported therefore, not exposing the
         models relevant to PASSTHROUGH as identities";
      type types:ncs_template_iface_model;
      // NCS drop default statement
    }
    leaf admin_state_up {
      description
        "The administrative state of the resource, which is up (true) or down (false).";
      type string;
    }
    leaf network {
      description
        "Network to which this interface needs to be attached.";
      type types:ncs_template_escnetname;
      // NCS drop mandatory statement
    }
    choice single_subnet_or_multiple {
      case single {
        leaf subnet {
          description
            "Subnet within the network to where the port needs to be created.";
          type types:ncs_template_escnetname;
        }
        leaf ip_address {
          description
            "Static IP address for this interface";
          type types:ncs_template_escipaddr;
          // NCS drop must statement
        }
      }
      case multiple {
        uses ncs_template_esc_interface_addresses;
      }
    }
    leaf anycast_address {
      description
        "Anycast address corresponding to this interface";
      type types:ncs_template_escipaddr;
    }
    leaf public_ip_address {
      description
        "Public IP address for this interface";
      type types:ncs_template_escipaddr;
    }
    leaf mac_address {
      description
        "Static MAC address for this interface";
      type types:ncs_template_escmacaddr;
      // NCS drop must statement
    }
    leaf port_security_enabled {
      description
        "Whether the port security is enabled at port level";
      type string;
    }
    container bandwidth {
      leaf min {
        description
          "Minimum bandwidth required for this interface in Mbps";
        type string;
      }
      leaf max {
        description
          "Maximum bandwidth required for this interface in Mbps";
        type string;
      }
    }
    container security_groups {
      description
        "Container for security group(s) set for this instance";
      leaf-list security_group {
        // NCS patched for predictable order
        ordered-by user;
        description
          "IP filter rules that determine access control for the VM instance";
        type types:ncs_template_escnetname;
      }
    }
    container allowed_address_pairs {
      description
        "The allowed address is allows one to specify
         arbitrary mac_address/ip_address(cidr) pairs that are
         allowed to pass through a port regardless of subnet.";
      list network {
        // NCS patched for predictable order
        ordered-by user;
        key "name";
        description
          "Network allowed on this interface";
        leaf name {
          description
            "Network name or uuid";
          type types:ncs_template_escnetname;
          // NCS drop mandatory statement
        }
      }
      list address {
        // NCS patched for predictable order
        ordered-by user;
        key "ip_address";
        description
          "Allowed address on this interface";
        leaf ip_address {
          description
            "IP address for this network.";
          type types:ncs_template_escipaddr;
          // NCS drop mandatory statement
        }
        choice subnet_netmask_or_prefix_len {
          case netmask {
            leaf netmask {
              description
                "Netmask for subnet address.";
              type types:ncs_template_escipaddr;
            }
          }
          case ip_prefix {
            leaf ip_prefix {
              description
                "Prefix length for subnet address, represented by integer.
                 For IPv4 address range is 0 - 32.
                 For IPv6 address range is 0 - 128.";
              type types:ncs_template_esc_ip_prefix;
            }
          }
        }
      }
    }
    container binding_profile {
      list property {
        // NCS patched for predictable order
        ordered-by user;
        key "name";
        description
          "Binding profile property";
        leaf name {
          description
            "Property name";
          type string;
          // NCS drop mandatory statement
        }
        leaf value {
          description
            "Property value";
          type string;
        }
      }
    }
    uses port_forwarding:ncs_template_esc_port_forwarding;
  }

  grouping ncs_template_esc_interface {
    container interfaces {
      description
        "Specification of number of interfaces and properties for each
         interface. The order of the interfaces specified here does
         not correspond to the order of the interfaces in the VM.";
      list interface {
        // NCS patched for predictable order
        ordered-by user;
        key "nicid";
        leaf nicid {
          description
            "ID for the interfaces. This determines the order
             in which interfaces are presented to the guest VM";
          type string;
          // NCS drop mandatory statement
        }
        choice interface_target {
          case new_iface {
            description
              "The interface is new and ESC will create it.";
            uses ncs_template_esc_interface_details;
          }
          case existing_port {
            leaf port {
              description
                "The interface refers to an existing port.";
              type types:ncs_template_escnetname;
            }
          }
        }
      }
    }
  }

  grouping ncs_rpc_notif_esc_interface_addresses {
    container addresses {
      list address {
        key "address_id";
        leaf address_id {
          description
            "Id for the address in address list.";
          type uint16;
          mandatory true;
        }
        leaf subnet {
          description
            "Subnet name or uuid for allocating IP to this port";
          type types:ncs_rpc_notif_escnetname;
        }
        leaf ip_address {
          description
            "Static IP address for this specific subnet";
          type types:ncs_rpc_notif_escipaddr;
          must '../../../../../scaling/max_active = 1 or count(../../../../../scaling/static_ip_address_pool) > 0' {
            tailf:xpath-root 3;
            error-message "Static ip address pools must be configured when static ip addresses are configured.";
          }
        }
      }
    }
  }

  grouping ncs_rpc_notif_esc_interface_details {
    leaf type {
      description
        "Interface Type: virtual/passthru";
      type types:ncs_rpc_notif_iface_type;
      default "virtual";
    }
    leaf vim_interface_name {
      description
        "User specified name for the interface on the VIM";
      type types:ncs_rpc_notif_escname;
    }
    leaf model {
      description
        "In case of virtual: e1000 or virtio. In case of passthrough:
         Model of the NIC. This will be specific to the data center. Data
         centers may have NICs that support virtual functions from
         different vendors, like Intel, Cisco etc. Passthrough is
         not currently supported therefore, not exposing the
         models relevant to PASSTHROUGH as identities";
      type types:ncs_rpc_notif_iface_model;
      default "virtio";
    }
    leaf admin_state_up {
      description
        "The administrative state of the resource, which is up (true) or down (false).";
      type boolean;
    }
    leaf network {
      description
        "Network to which this interface needs to be attached.";
      type types:ncs_rpc_notif_escnetname;
      mandatory true;
    }
    choice single_subnet_or_multiple {
      case single {
        leaf subnet {
          description
            "Subnet within the network to where the port needs to be created.";
          type types:ncs_rpc_notif_escnetname;
        }
        leaf ip_address {
          description
            "Static IP address for this interface";
          type types:ncs_rpc_notif_escipaddr;
          must '../../../scaling/max_active = 1 or count(../../../scaling/static_ip_address_pool) > 0' {
            tailf:xpath-root 3;
            error-message "Static ip address pools must be configured when static ip addresses are configured.";
          }
        }
      }
      case multiple {
        uses ncs_rpc_notif_esc_interface_addresses;
      }
    }
    leaf anycast_address {
      description
        "Anycast address corresponding to this interface";
      type types:ncs_rpc_notif_escipaddr;
    }
    leaf public_ip_address {
      description
        "Public IP address for this interface";
      type types:ncs_rpc_notif_escipaddr;
    }
    leaf mac_address {
      description
        "Static MAC address for this interface";
      type types:ncs_rpc_notif_escmacaddr;
      must 'count(../../../scaling/static_mac_address_pool) > 0' {
        tailf:xpath-root 3;
        error-message "Static mac address pools must be configured when static mac addresses are configured.";
      }
    }
    leaf port_security_enabled {
      description
        "Whether the port security is enabled at port level";
      type boolean;
    }
    container bandwidth {
      leaf min {
        description
          "Minimum bandwidth required for this interface in Mbps";
        type int32;
      }
      leaf max {
        description
          "Maximum bandwidth required for this interface in Mbps";
        type int32;
      }
    }
    container security_groups {
      description
        "Container for security group(s) set for this instance";
      leaf-list security_group {
        description
          "IP filter rules that determine access control for the VM instance";
        type types:ncs_rpc_notif_escnetname;
      }
    }
    container allowed_address_pairs {
      description
        "The allowed address is allows one to specify
         arbitrary mac_address/ip_address(cidr) pairs that are
         allowed to pass through a port regardless of subnet.";
      list network {
        key "name";
        description
          "Network allowed on this interface";
        leaf name {
          description
            "Network name or uuid";
          type types:ncs_rpc_notif_escnetname;
          mandatory true;
        }
      }
      list address {
        key "ip_address";
        description
          "Allowed address on this interface";
        leaf ip_address {
          description
            "IP address for this network.";
          type types:ncs_rpc_notif_escipaddr;
          mandatory true;
        }
        choice subnet_netmask_or_prefix_len {
          case netmask {
            leaf netmask {
              description
                "Netmask for subnet address.";
              type types:ncs_rpc_notif_escipaddr;
            }
          }
          case ip_prefix {
            leaf ip_prefix {
              description
                "Prefix length for subnet address, represented by integer.
                 For IPv4 address range is 0 - 32.
                 For IPv6 address range is 0 - 128.";
              type types:ncs_rpc_notif_esc_ip_prefix;
            }
          }
        }
      }
    }
    container binding_profile {
      list property {
        key "name";
        description
          "Binding profile property";
        leaf name {
          description
            "Property name";
          type string;
          mandatory true;
        }
        leaf value {
          description
            "Property value";
          type string;
        }
      }
    }
    uses port_forwarding:ncs_rpc_notif_esc_port_forwarding;
  }

  grouping ncs_rpc_notif_esc_interface {
    container interfaces {
      description
        "Specification of number of interfaces and properties for each
         interface. The order of the interfaces specified here does
         not correspond to the order of the interfaces in the VM.";
      list interface {
        key "nicid";
        leaf nicid {
          description
            "ID for the interfaces. This determines the order
             in which interfaces are presented to the guest VM";
          type uint16;
          mandatory true;
        }
        choice interface_target {
          case new_iface {
            description
              "The interface is new and ESC will create it.";
            uses ncs_rpc_notif_esc_interface_details;
          }
          case existing_port {
            leaf port {
              description
                "The interface refers to an existing port.";
              type types:ncs_rpc_notif_escnetname;
            }
          }
        }
      }
    }
  }

  grouping live_ncs_esc_interface_addresses {
    container addresses {
      list address {
        key "address_id";
        leaf address_id {
          description
            "Id for the address in address list.";
          type uint16;
          // NCS drop mandatory statement
        }
        leaf subnet {
          description
            "Subnet name or uuid for allocating IP to this port";
          type types:live_ncs_escnetname;
        }
        leaf ip_address {
          description
            "Static IP address for this specific subnet";
          type types:live_ncs_escipaddr;
          // NCS drop must statement
        }
      }
    }
  }

  grouping live_ncs_esc_interface_details {
    leaf type {
      description
        "Interface Type: virtual/passthru";
      type types:live_ncs_iface_type;
      // NCS drop default statement
    }
    leaf vim_interface_name {
      description
        "User specified name for the interface on the VIM";
      type types:live_ncs_escname;
    }
    leaf model {
      description
        "In case of virtual: e1000 or virtio. In case of passthrough:
         Model of the NIC. This will be specific to the data center. Data
         centers may have NICs that support virtual functions from
         different vendors, like Intel, Cisco etc. Passthrough is
         not currently supported therefore, not exposing the
         models relevant to PASSTHROUGH as identities";
      type types:live_ncs_iface_model;
      // NCS drop default statement
    }
    leaf admin_state_up {
      description
        "The administrative state of the resource, which is up (true) or down (false).";
      type boolean;
    }
    leaf network {
      description
        "Network to which this interface needs to be attached.";
      type types:live_ncs_escnetname;
      // NCS drop mandatory statement
    }
    choice single_subnet_or_multiple {
      case single {
        leaf subnet {
          description
            "Subnet within the network to where the port needs to be created.";
          type types:live_ncs_escnetname;
        }
        leaf ip_address {
          description
            "Static IP address for this interface";
          type types:live_ncs_escipaddr;
          // NCS drop must statement
        }
      }
      case multiple {
        uses live_ncs_esc_interface_addresses;
      }
    }
    leaf anycast_address {
      description
        "Anycast address corresponding to this interface";
      type types:live_ncs_escipaddr;
    }
    leaf public_ip_address {
      description
        "Public IP address for this interface";
      type types:live_ncs_escipaddr;
    }
    leaf mac_address {
      description
        "Static MAC address for this interface";
      type types:live_ncs_escmacaddr;
      // NCS drop must statement
    }
    leaf port_security_enabled {
      description
        "Whether the port security is enabled at port level";
      type boolean;
    }
    container bandwidth {
      leaf min {
        description
          "Minimum bandwidth required for this interface in Mbps";
        type int32;
      }
      leaf max {
        description
          "Maximum bandwidth required for this interface in Mbps";
        type int32;
      }
    }
    container security_groups {
      description
        "Container for security group(s) set for this instance";
      leaf-list security_group {
        description
          "IP filter rules that determine access control for the VM instance";
        type types:live_ncs_escnetname;
      }
    }
    container allowed_address_pairs {
      description
        "The allowed address is allows one to specify
         arbitrary mac_address/ip_address(cidr) pairs that are
         allowed to pass through a port regardless of subnet.";
      list network {
        key "name";
        description
          "Network allowed on this interface";
        leaf name {
          description
            "Network name or uuid";
          type types:live_ncs_escnetname;
          // NCS drop mandatory statement
        }
      }
      list address {
        key "ip_address";
        description
          "Allowed address on this interface";
        leaf ip_address {
          description
            "IP address for this network.";
          type types:live_ncs_escipaddr;
          // NCS drop mandatory statement
        }
        choice subnet_netmask_or_prefix_len {
          case netmask {
            leaf netmask {
              description
                "Netmask for subnet address.";
              type types:live_ncs_escipaddr;
            }
          }
          case ip_prefix {
            leaf ip_prefix {
              description
                "Prefix length for subnet address, represented by integer.
                 For IPv4 address range is 0 - 32.
                 For IPv6 address range is 0 - 128.";
              type types:live_ncs_esc_ip_prefix;
            }
          }
        }
      }
    }
    container binding_profile {
      list property {
        key "name";
        description
          "Binding profile property";
        leaf name {
          description
            "Property name";
          type string;
          // NCS drop mandatory statement
        }
        leaf value {
          description
            "Property value";
          type string;
        }
      }
    }
    uses port_forwarding:live_ncs_esc_port_forwarding;
  }

  grouping live_ncs_esc_interface {
    container interfaces {
      description
        "Specification of number of interfaces and properties for each
         interface. The order of the interfaces specified here does
         not correspond to the order of the interfaces in the VM.";
      list interface {
        key "nicid";
        leaf nicid {
          description
            "ID for the interfaces. This determines the order
             in which interfaces are presented to the guest VM";
          type uint16;
          // NCS drop mandatory statement
        }
        choice interface_target {
          case new_iface {
            description
              "The interface is new and ESC will create it.";
            uses live_ncs_esc_interface_details;
          }
          case existing_port {
            leaf port {
              description
                "The interface refers to an existing port.";
              type types:live_ncs_escnetname;
            }
          }
        }
      }
    }
  }

  grouping esc_interface_addresses {
    container addresses {
      list address {
        key "address_id";
        leaf address_id {
          description
            "Id for the address in address list.";
          type uint16;
          mandatory true;
        }
        leaf subnet {
          description
            "Subnet name or uuid for allocating IP to this port";
          type types:escnetname;
        }
        leaf ip_address {
          description
            "Static IP address for this specific subnet";
          type types:escipaddr;
          must '../../../../../scaling/max_active = 1 or count(../../../../../scaling/static_ip_address_pool) > 0' {
            tailf:xpath-root 3;
            error-message "Static ip address pools must be configured when static ip addresses are configured.";
          }
        }
      }
    }
  }

  grouping esc_interface_details {
    leaf type {
      description
        "Interface Type: virtual/passthru";
      type types:iface_type;
      default "virtual";
    }
    leaf vim_interface_name {
      description
        "User specified name for the interface on the VIM";
      type types:escname;
    }
    leaf model {
      description
        "In case of virtual: e1000 or virtio. In case of passthrough:
         Model of the NIC. This will be specific to the data center. Data
         centers may have NICs that support virtual functions from
         different vendors, like Intel, Cisco etc. Passthrough is
         not currently supported therefore, not exposing the
         models relevant to PASSTHROUGH as identities";
      type types:iface_model;
      default "virtio";
    }
    leaf admin_state_up {
      description
        "The administrative state of the resource, which is up (true) or down (false).";
      type boolean;
    }
    leaf network {
      description
        "Network to which this interface needs to be attached.";
      type types:escnetname;
      mandatory true;
    }
    choice single_subnet_or_multiple {
      case single {
        leaf subnet {
          description
            "Subnet within the network to where the port needs to be created.";
          type types:escnetname;
        }
        leaf ip_address {
          description
            "Static IP address for this interface";
          type types:escipaddr;
          must '../../../scaling/max_active = 1 or count(../../../scaling/static_ip_address_pool) > 0' {
            tailf:xpath-root 3;
            error-message "Static ip address pools must be configured when static ip addresses are configured.";
          }
        }
      }
      case multiple {
        uses esc_interface_addresses;
      }
    }
    leaf anycast_address {
      description
        "Anycast address corresponding to this interface";
      type types:escipaddr;
    }
    leaf public_ip_address {
      description
        "Public IP address for this interface";
      type types:escipaddr;
    }
    leaf mac_address {
      description
        "Static MAC address for this interface";
      type types:escmacaddr;
      must 'count(../../../scaling/static_mac_address_pool) > 0' {
        tailf:xpath-root 3;
        error-message "Static mac address pools must be configured when static mac addresses are configured.";
      }
    }
    leaf port_security_enabled {
      description
        "Whether the port security is enabled at port level";
      type boolean;
    }
    container bandwidth {
      leaf min {
        description
          "Minimum bandwidth required for this interface in Mbps";
        type int32;
      }
      leaf max {
        description
          "Maximum bandwidth required for this interface in Mbps";
        type int32;
      }
    }
    container security_groups {
      description
        "Container for security group(s) set for this instance";
      leaf-list security_group {
        description
          "IP filter rules that determine access control for the VM instance";
        type types:escnetname;
      }
    }
    container allowed_address_pairs {
      description
        "The allowed address is allows one to specify
         arbitrary mac_address/ip_address(cidr) pairs that are
         allowed to pass through a port regardless of subnet.";
      list network {
        key "name";
        description
          "Network allowed on this interface";
        leaf name {
          description
            "Network name or uuid";
          type types:escnetname;
          mandatory true;
        }
      }
      list address {
        key "ip_address";
        description
          "Allowed address on this interface";
        leaf ip_address {
          description
            "IP address for this network.";
          type types:escipaddr;
          mandatory true;
        }
        choice subnet_netmask_or_prefix_len {
          case netmask {
            leaf netmask {
              description
                "Netmask for subnet address.";
              type types:escipaddr;
            }
          }
          case ip_prefix {
            leaf ip_prefix {
              description
                "Prefix length for subnet address, represented by integer.
                 For IPv4 address range is 0 - 32.
                 For IPv6 address range is 0 - 128.";
              type types:esc_ip_prefix;
            }
          }
        }
      }
    }
    container binding_profile {
      list property {
        key "name";
        description
          "Binding profile property";
        leaf name {
          description
            "Property name";
          type string;
          mandatory true;
        }
        leaf value {
          description
            "Property value";
          type string;
        }
      }
    }
    uses port_forwarding:esc_port_forwarding;
  }

  grouping esc_interface {
    container interfaces {
      description
        "Specification of number of interfaces and properties for each
         interface. The order of the interfaces specified here does
         not correspond to the order of the interfaces in the VM.";
      list interface {
        key "nicid";
        leaf nicid {
          description
            "ID for the interfaces. This determines the order
             in which interfaces are presented to the guest VM";
          type uint16;
          mandatory true;
        }
        choice interface_target {
          case new_iface {
            description
              "The interface is new and ESC will create it.";
            uses esc_interface_details;
          }
          case existing_port {
            leaf port {
              description
                "The interface refers to an existing port.";
              type types:escnetname;
            }
          }
        }
      }
    }
  }
}
