submodule esc_notifications {
  // Generated by yanger -t ncs
  tailf:mount-id esc-nc-1.0:esc-nc-1.0;

  belongs-to esc {
    prefix notifications;
  }

  import tailf-common {
    prefix tailf;
  }
  import esc_types {
    prefix types;
  }
  import esc_opdata_interface {
    prefix interface;
  }
  import esc_opdata_volumes {
    prefix volumes;
  }
  import esc_property {
    prefix property;
  }
  import "esc-nc-1.0" {
    prefix "esc-nc-1.0";
  }
  import tailf-ncs {
    prefix ncs;
  }

  organization
    "Cisco Systems";
  contact
    "Shesha Sreenivasamurthy <shesha@cisco.com>";

  revision 2020-03-25 {
    description
      "Move notification vmlcevents leaves to a grouping named vmlcevents for modularity";
  }
  revision 2018-07-10 {
    description
      "Added vim_network_name to escEvent";
  }
  revision 2018-07-05 {
    description
      "Add vdc field under vm_instance";
  }
  revision 2018-04-24 {
    description
      "Removed the uuid type restriction from vmid";
  }
  revision 2018-02-07 {
    description
      "Added generated_vmname to viminfo";
  }
  revision 2017-09-25 {
    description
      "Added file_server_id to escEvent";
  }
  revision 2017-05-16 {
    description
      "Added vmname to viminfo";
  }
  revision 2017-05-01 {
    description
      "Rename esc tenant attribute multi_vim to vim_mapping";
  }
  revision 2017-03-27 {
    description
      "Adding VIM related info to the deploy notifications";
  }
  revision 2017-03-20 {
    description
      "Added volume element to escEvent for notifications";
  }
  revision 2017-03-06 {
    description
      "Add tenant's multi_vim attribute to notification";
  }
  revision 2017-01-19 {
    description
      "Added a config_data element to escEvent so that notifications can receive config_data. US8607";
  }
  revision 2016-10-06 {
    description
      "Adding vim_connector_id and vim_user_id leaf to notifs";
  }
  revision 2016-08-04 {
    description
      "Adding properties in vminfo";
  }
  revision 2016-01-20 {
    description
      "Adding tenant UUID leaf to notifs";
  }
  revision 2015-07-16 {
    description
      "Notifications adding interface details for VM , Recovery and Scaling related events";
  }
  revision 2015-07-14 {
    description
      "Notifications adding interface details for VM , Recovery and Scaling related events";
  }
  revision 2015-06-29 {
    description
      "Notifications for image and flavor creation not associated
       with service";
  }
  revision 2015-06-10 {
    description
      "added hostname to vminfo";
  }
  revision 2014-10-03 {
    description
      "Notifications generated by ESC for consumption by its north
       bound clients";
  }

  grouping ncs_template_vminfo {
    leaf vmid {
      description
        "ID of the VM";
      type string;
    }
    leaf vmname {
      description
        "Generated or custom name of the VM";
      type string;
    }
    leaf generated_vmname {
      description
        "Generated name of the VM";
      type string;
    }
    leaf vim_id {
      description
        "ID of the VIM that is used internally by ESC";
      type types:ncs_template_escname;
    }
    leaf vim_project {
      description
        "Name of the project that this VM belongs to";
      type string;
    }
    leaf vim_project_id {
      description
        "External project UUID of this VIM project";
      type string;
    }
    leaf hostid {
      description
        "ID of the HOST where VM is running that is used
         internally by ESC";
      type string;
    }
    leaf hostname {
      description
        "Name of the HOST where VM is running that is used
         internally by ESC";
      type string;
      tailf:code-name "esc_hostname";
    }
    leaf vdc {
      description
        "VMware vCloud Director org virtual data center.";
      type string;
    }
    leaf software_version {
      description
        "Software version of the VM";
      type types:ncs_template_escname;
    }
    uses interface:ncs_template_esc_opdata_interface;
    uses volumes:ncs_template_esc_opdata_deployment_volumes;
    uses property:ncs_template_property_list_definition;
  }

  grouping ncs_template_escevents {
    leaf status {
      description
        "The event that is being notified is success or a failure";
      type types:ncs_template_status;
      // NCS drop mandatory statement
    }
    leaf status_code {
      description
        "The status code of the event notification";
      type string;
      // NCS drop default statement
    }
    leaf status_message {
      description
        "Description of the status code";
      type string;
      // NCS drop mandatory statement
    }
    leaf user_name {
      description
        "Name user that last modifed this resource, used for auditing purposes";
      type types:ncs_template_escname;
    }
    leaf volume {
      description
        "Volume name that was created or delete";
      type string;
    }
    leaf network {
      description
        "Network name that was created or deleted";
      type string;
    }
    leaf vim_network_name {
      description
        "Network name as-is on the VIM if different from esc network name reference, for ESC multiVIM network support";
      type string;
    }
    leaf subnet {
      description
        "Subnet name that was created or deleted";
      type string;
    }
    leaf image {
      description
        "Image name that was created or deleted";
      type string;
    }
    leaf flavor {
      description
        "Flavor name that was created or deleted";
      type string;
    }
    leaf svcname {
      description
        "Name of the service to which this VM belongs to";
      type types:ncs_template_escname;
    }
    leaf svcversion {
      description
        "Version of the service to which this VM belongs to";
      type types:ncs_template_escversion;
    }
    leaf depname {
      description
        "Name of the deployment to which this VM belongs to";
      type types:ncs_template_escname;
    }
    leaf tenant {
      description
        "Tenant name that was created or deleted or Name of the
            tenant to which this VM belongs to";
      type types:ncs_template_escname;
    }
    leaf tenant_id {
      description
        "External tenant UUID of the tenant";
      type string;
    }
    leaf vim_mapping {
      description
        "Attribute to specify if the tenant is an esc tenant or if it is mapped
         to a vim tenant";
      type string;
    }
    leaf svcid {
      description
        "ID of the service that is used internally by ESC to
         track the service";
      type string;
    }
    leaf depid {
      description
        "ID of the deployment that is used internally by ESC
         to track the deployment";
      type string;
    }
    leaf vm_group {
      description
        "Group/Type of VM to which the VMs specified in
         vm_source and vm_target belong";
      type types:ncs_template_escname;
    }
    leaf vim_connector_id {
      description
        "Vim connector id that was created, deleted or updated";
      type types:ncs_template_escname;
    }
    leaf vim_user_id {
      description
        "vim user id that was created, deleted or updated";
      type string;
    }
    leaf file_server_id {
      description
        "File Server Id that was created, deleted or updated";
      type types:ncs_template_escname;
    }
    container vm_source {
      description
        "Information of the VM that was:
                        Deployed or
                        Undeployed or
                        Overloaded or
                        Underloaded or
                        Undeployed because of any un-natural reasons";
      uses ncs_template_vminfo;
    }
    container vm_target {
      description
        "Information of the VM that was:
         Deployed when vm_source contains
         information of overloaded VM Undeployed, and will
         be same as vm_source when vm_source contains
         information of underloaded VM Deployed when
         vm_source contains information of the VM that died
         for any un-natural reasons";
      uses ncs_template_vminfo;
    }
    container policy {
      leaf condition {
        description
          "The policy condition that triggered this notify event";
        type types:ncs_template_policy_condition_type;
      }
      leaf action {
        description
          "The policy action name of the notify event";
        type string;
      }
      uses property:ncs_template_property_list_definition;
    }
    container event {
      description
        "This lest us know what event is this notification notifying.
         Additionally, from this one can infer what information
         vm_source and vm_target are referring to.";
      leaf type {
        description
          "Type of the event. As defined in EDCS: 1312696";
        type types:ncs_template_event_types;
        // NCS drop mandatory statement
      }
      leaf name {
        description
          "Name of the event. This is user defined in the datamodel.
           /esc_datamode/services/service_definition/
            vm_group/kpi_data/kpi/event_name";
        type string;
      }
      leaf threshold {
        description
          "Threshold value that was compared against that caused this event
           to be generated";
        type string;
      }
      leaf value {
        description
          "Actual value of the variable tracked for
           scale-out/scale-in";
        type string;
      }
      leaf details {
        description
          "Human-readable description";
        type string;
      }
    }
  }

  grouping ncs_rpc_notif_vminfo {
    leaf vmid {
      description
        "ID of the VM";
      type string;
    }
    leaf vmname {
      description
        "Generated or custom name of the VM";
      type string;
    }
    leaf generated_vmname {
      description
        "Generated name of the VM";
      type string;
    }
    leaf vim_id {
      description
        "ID of the VIM that is used internally by ESC";
      type types:ncs_rpc_notif_escname;
    }
    leaf vim_project {
      description
        "Name of the project that this VM belongs to";
      type string;
    }
    leaf vim_project_id {
      description
        "External project UUID of this VIM project";
      type string;
    }
    leaf hostid {
      description
        "ID of the HOST where VM is running that is used
         internally by ESC";
      type string;
    }
    leaf hostname {
      description
        "Name of the HOST where VM is running that is used
         internally by ESC";
      type string;
      tailf:code-name "esc_hostname";
    }
    leaf vdc {
      description
        "VMware vCloud Director org virtual data center.";
      type string;
    }
    leaf software_version {
      description
        "Software version of the VM";
      type types:ncs_rpc_notif_escname;
    }
    uses interface:ncs_rpc_notif_esc_opdata_interface;
    uses volumes:ncs_rpc_notif_esc_opdata_deployment_volumes;
    uses property:ncs_rpc_notif_property_list_definition;
  }

  grouping ncs_rpc_notif_escevents {
    leaf status {
      description
        "The event that is being notified is success or a failure";
      type types:ncs_rpc_notif_status;
      mandatory true;
    }
    leaf status_code {
      description
        "The status code of the event notification";
      type int16;
      default "0";
    }
    leaf status_message {
      description
        "Description of the status code";
      type string;
      mandatory true;
    }
    leaf user_name {
      description
        "Name user that last modifed this resource, used for auditing purposes";
      type types:ncs_rpc_notif_escname;
    }
    leaf volume {
      description
        "Volume name that was created or delete";
      type string;
    }
    leaf network {
      description
        "Network name that was created or deleted";
      type string;
    }
    leaf vim_network_name {
      description
        "Network name as-is on the VIM if different from esc network name reference, for ESC multiVIM network support";
      type string;
    }
    leaf subnet {
      description
        "Subnet name that was created or deleted";
      type string;
    }
    leaf image {
      description
        "Image name that was created or deleted";
      type string;
    }
    leaf flavor {
      description
        "Flavor name that was created or deleted";
      type string;
    }
    leaf svcname {
      description
        "Name of the service to which this VM belongs to";
      type types:ncs_rpc_notif_escname;
    }
    leaf svcversion {
      description
        "Version of the service to which this VM belongs to";
      type types:ncs_rpc_notif_escversion;
    }
    leaf depname {
      description
        "Name of the deployment to which this VM belongs to";
      type types:ncs_rpc_notif_escname;
    }
    leaf tenant {
      description
        "Tenant name that was created or deleted or Name of the
            tenant to which this VM belongs to";
      type types:ncs_rpc_notif_escname;
    }
    leaf tenant_id {
      description
        "External tenant UUID of the tenant";
      type string;
    }
    leaf vim_mapping {
      description
        "Attribute to specify if the tenant is an esc tenant or if it is mapped
         to a vim tenant";
      type boolean;
    }
    leaf svcid {
      description
        "ID of the service that is used internally by ESC to
         track the service";
      type string {
        length "1..41";
      }
    }
    leaf depid {
      description
        "ID of the deployment that is used internally by ESC
         to track the deployment";
      type string {
        length "1..41";
      }
    }
    leaf vm_group {
      description
        "Group/Type of VM to which the VMs specified in
         vm_source and vm_target belong";
      type types:ncs_rpc_notif_escname;
    }
    leaf vim_connector_id {
      description
        "Vim connector id that was created, deleted or updated";
      type types:ncs_rpc_notif_escname;
    }
    leaf vim_user_id {
      description
        "vim user id that was created, deleted or updated";
      type string;
    }
    leaf file_server_id {
      description
        "File Server Id that was created, deleted or updated";
      type types:ncs_rpc_notif_escname;
    }
    container vm_source {
      description
        "Information of the VM that was:
                        Deployed or
                        Undeployed or
                        Overloaded or
                        Underloaded or
                        Undeployed because of any un-natural reasons";
      uses ncs_rpc_notif_vminfo;
    }
    container vm_target {
      description
        "Information of the VM that was:
         Deployed when vm_source contains
         information of overloaded VM Undeployed, and will
         be same as vm_source when vm_source contains
         information of underloaded VM Deployed when
         vm_source contains information of the VM that died
         for any un-natural reasons";
      uses ncs_rpc_notif_vminfo;
    }
    container policy {
      leaf condition {
        description
          "The policy condition that triggered this notify event";
        type types:ncs_rpc_notif_policy_condition_type;
      }
      leaf action {
        description
          "The policy action name of the notify event";
        type string;
      }
      uses property:ncs_rpc_notif_property_list_definition;
    }
    container event {
      description
        "This lest us know what event is this notification notifying.
         Additionally, from this one can infer what information
         vm_source and vm_target are referring to.";
      leaf type {
        description
          "Type of the event. As defined in EDCS: 1312696";
        type types:ncs_rpc_notif_event_types;
        mandatory true;
      }
      leaf name {
        description
          "Name of the event. This is user defined in the datamodel.
           /esc_datamode/services/service_definition/
            vm_group/kpi_data/kpi/event_name";
        type string;
      }
      leaf threshold {
        description
          "Threshold value that was compared against that caused this event
           to be generated";
        type string {
          length "1..64";
        }
      }
      leaf value {
        description
          "Actual value of the variable tracked for
           scale-out/scale-in";
        type string {
          length "1..64";
        }
      }
      leaf details {
        description
          "Human-readable description";
        type string {
          length "1..1024";
        }
      }
    }
  }

  grouping live_ncs_vminfo {
    leaf vmid {
      description
        "ID of the VM";
      type string;
    }
    leaf vmname {
      description
        "Generated or custom name of the VM";
      type string;
    }
    leaf generated_vmname {
      description
        "Generated name of the VM";
      type string;
    }
    leaf vim_id {
      description
        "ID of the VIM that is used internally by ESC";
      type types:live_ncs_escname;
    }
    leaf vim_project {
      description
        "Name of the project that this VM belongs to";
      type string;
    }
    leaf vim_project_id {
      description
        "External project UUID of this VIM project";
      type string;
    }
    leaf hostid {
      description
        "ID of the HOST where VM is running that is used
         internally by ESC";
      type string;
    }
    leaf hostname {
      description
        "Name of the HOST where VM is running that is used
         internally by ESC";
      type string;
      tailf:code-name "esc_hostname";
    }
    leaf vdc {
      description
        "VMware vCloud Director org virtual data center.";
      type string;
    }
    leaf software_version {
      description
        "Software version of the VM";
      type types:live_ncs_escname;
    }
    uses interface:live_ncs_esc_opdata_interface;
    uses volumes:live_ncs_esc_opdata_deployment_volumes;
    uses property:live_ncs_property_list_definition;
  }

  grouping live_ncs_escevents {
    leaf status {
      description
        "The event that is being notified is success or a failure";
      type types:live_ncs_status;
      // NCS drop mandatory statement
    }
    leaf status_code {
      description
        "The status code of the event notification";
      type int16;
      // NCS drop default statement
    }
    leaf status_message {
      description
        "Description of the status code";
      type string;
      // NCS drop mandatory statement
    }
    leaf user_name {
      description
        "Name user that last modifed this resource, used for auditing purposes";
      type types:live_ncs_escname;
    }
    leaf volume {
      description
        "Volume name that was created or delete";
      type string;
    }
    leaf network {
      description
        "Network name that was created or deleted";
      type string;
    }
    leaf vim_network_name {
      description
        "Network name as-is on the VIM if different from esc network name reference, for ESC multiVIM network support";
      type string;
    }
    leaf subnet {
      description
        "Subnet name that was created or deleted";
      type string;
    }
    leaf image {
      description
        "Image name that was created or deleted";
      type string;
    }
    leaf flavor {
      description
        "Flavor name that was created or deleted";
      type string;
    }
    leaf svcname {
      description
        "Name of the service to which this VM belongs to";
      type types:live_ncs_escname;
    }
    leaf svcversion {
      description
        "Version of the service to which this VM belongs to";
      type types:live_ncs_escversion;
    }
    leaf depname {
      description
        "Name of the deployment to which this VM belongs to";
      type types:live_ncs_escname;
    }
    leaf tenant {
      description
        "Tenant name that was created or deleted or Name of the
            tenant to which this VM belongs to";
      type types:live_ncs_escname;
    }
    leaf tenant_id {
      description
        "External tenant UUID of the tenant";
      type string;
    }
    leaf vim_mapping {
      description
        "Attribute to specify if the tenant is an esc tenant or if it is mapped
         to a vim tenant";
      type boolean;
    }
    leaf svcid {
      description
        "ID of the service that is used internally by ESC to
         track the service";
      type string {
        length "1..41";
      }
    }
    leaf depid {
      description
        "ID of the deployment that is used internally by ESC
         to track the deployment";
      type string {
        length "1..41";
      }
    }
    leaf vm_group {
      description
        "Group/Type of VM to which the VMs specified in
         vm_source and vm_target belong";
      type types:live_ncs_escname;
    }
    leaf vim_connector_id {
      description
        "Vim connector id that was created, deleted or updated";
      type types:live_ncs_escname;
    }
    leaf vim_user_id {
      description
        "vim user id that was created, deleted or updated";
      type string;
    }
    leaf file_server_id {
      description
        "File Server Id that was created, deleted or updated";
      type types:live_ncs_escname;
    }
    container vm_source {
      description
        "Information of the VM that was:
                        Deployed or
                        Undeployed or
                        Overloaded or
                        Underloaded or
                        Undeployed because of any un-natural reasons";
      uses live_ncs_vminfo;
    }
    container vm_target {
      description
        "Information of the VM that was:
         Deployed when vm_source contains
         information of overloaded VM Undeployed, and will
         be same as vm_source when vm_source contains
         information of underloaded VM Deployed when
         vm_source contains information of the VM that died
         for any un-natural reasons";
      uses live_ncs_vminfo;
    }
    container policy {
      leaf condition {
        description
          "The policy condition that triggered this notify event";
        type types:live_ncs_policy_condition_type;
      }
      leaf action {
        description
          "The policy action name of the notify event";
        type string;
      }
      uses property:live_ncs_property_list_definition;
    }
    container event {
      description
        "This lest us know what event is this notification notifying.
         Additionally, from this one can infer what information
         vm_source and vm_target are referring to.";
      leaf type {
        description
          "Type of the event. As defined in EDCS: 1312696";
        type types:live_ncs_event_types;
        // NCS drop mandatory statement
      }
      leaf name {
        description
          "Name of the event. This is user defined in the datamodel.
           /esc_datamode/services/service_definition/
            vm_group/kpi_data/kpi/event_name";
        type string;
      }
      leaf threshold {
        description
          "Threshold value that was compared against that caused this event
           to be generated";
        type string {
          length "1..64";
        }
      }
      leaf value {
        description
          "Actual value of the variable tracked for
           scale-out/scale-in";
        type string {
          length "1..64";
        }
      }
      leaf details {
        description
          "Human-readable description";
        type string {
          length "1..1024";
        }
      }
    }
  }

  grouping vminfo {
    leaf vmid {
      description
        "ID of the VM";
      type string;
    }
    leaf vmname {
      description
        "Generated or custom name of the VM";
      type string;
    }
    leaf generated_vmname {
      description
        "Generated name of the VM";
      type string;
    }
    leaf vim_id {
      description
        "ID of the VIM that is used internally by ESC";
      type types:escname;
    }
    leaf vim_project {
      description
        "Name of the project that this VM belongs to";
      type string;
    }
    leaf vim_project_id {
      description
        "External project UUID of this VIM project";
      type string;
    }
    leaf hostid {
      description
        "ID of the HOST where VM is running that is used
         internally by ESC";
      type string;
    }
    leaf hostname {
      description
        "Name of the HOST where VM is running that is used
         internally by ESC";
      type string;
      tailf:code-name "esc_hostname";
    }
    leaf vdc {
      description
        "VMware vCloud Director org virtual data center.";
      type string;
    }
    leaf software_version {
      description
        "Software version of the VM";
      type types:escname;
    }
    uses interface:esc_opdata_interface;
    uses volumes:esc_opdata_deployment_volumes;
    uses property:property_list_definition;
  }

  grouping escevents {
    leaf status {
      description
        "The event that is being notified is success or a failure";
      type types:status;
      mandatory true;
    }
    leaf status_code {
      description
        "The status code of the event notification";
      type int16;
      default "0";
    }
    leaf status_message {
      description
        "Description of the status code";
      type string;
      mandatory true;
    }
    leaf user_name {
      description
        "Name user that last modifed this resource, used for auditing purposes";
      type types:escname;
    }
    leaf volume {
      description
        "Volume name that was created or delete";
      type string;
    }
    leaf network {
      description
        "Network name that was created or deleted";
      type string;
    }
    leaf vim_network_name {
      description
        "Network name as-is on the VIM if different from esc network name reference, for ESC multiVIM network support";
      type string;
    }
    leaf subnet {
      description
        "Subnet name that was created or deleted";
      type string;
    }
    leaf image {
      description
        "Image name that was created or deleted";
      type string;
    }
    leaf flavor {
      description
        "Flavor name that was created or deleted";
      type string;
    }
    leaf svcname {
      description
        "Name of the service to which this VM belongs to";
      type types:escname;
    }
    leaf svcversion {
      description
        "Version of the service to which this VM belongs to";
      type types:escversion;
    }
    leaf depname {
      description
        "Name of the deployment to which this VM belongs to";
      type types:escname;
    }
    leaf tenant {
      description
        "Tenant name that was created or deleted or Name of the
            tenant to which this VM belongs to";
      type types:escname;
    }
    leaf tenant_id {
      description
        "External tenant UUID of the tenant";
      type string;
    }
    leaf vim_mapping {
      description
        "Attribute to specify if the tenant is an esc tenant or if it is mapped
         to a vim tenant";
      type boolean;
    }
    leaf svcid {
      description
        "ID of the service that is used internally by ESC to
         track the service";
      type string {
        length "1..41";
      }
    }
    leaf depid {
      description
        "ID of the deployment that is used internally by ESC
         to track the deployment";
      type string {
        length "1..41";
      }
    }
    leaf vm_group {
      description
        "Group/Type of VM to which the VMs specified in
         vm_source and vm_target belong";
      type types:escname;
    }
    leaf vim_connector_id {
      description
        "Vim connector id that was created, deleted or updated";
      type types:escname;
    }
    leaf vim_user_id {
      description
        "vim user id that was created, deleted or updated";
      type string;
    }
    leaf file_server_id {
      description
        "File Server Id that was created, deleted or updated";
      type types:escname;
    }
    container vm_source {
      description
        "Information of the VM that was:
                        Deployed or
                        Undeployed or
                        Overloaded or
                        Underloaded or
                        Undeployed because of any un-natural reasons";
      uses vminfo;
    }
    container vm_target {
      description
        "Information of the VM that was:
         Deployed when vm_source contains
         information of overloaded VM Undeployed, and will
         be same as vm_source when vm_source contains
         information of underloaded VM Deployed when
         vm_source contains information of the VM that died
         for any un-natural reasons";
      uses vminfo;
    }
    container policy {
      leaf condition {
        description
          "The policy condition that triggered this notify event";
        type types:policy_condition_type;
      }
      leaf action {
        description
          "The policy action name of the notify event";
        type string;
      }
      uses property:property_list_definition;
    }
    container event {
      description
        "This lest us know what event is this notification notifying.
         Additionally, from this one can infer what information
         vm_source and vm_target are referring to.";
      leaf type {
        description
          "Type of the event. As defined in EDCS: 1312696";
        type types:event_types;
        mandatory true;
      }
      leaf name {
        description
          "Name of the event. This is user defined in the datamodel.
           /esc_datamode/services/service_definition/
            vm_group/kpi_data/kpi/event_name";
        type string;
      }
      leaf threshold {
        description
          "Threshold value that was compared against that caused this event
           to be generated";
        type string {
          length "1..64";
        }
      }
      leaf value {
        description
          "Actual value of the variable tracked for
           scale-out/scale-in";
        type string {
          length "1..64";
        }
      }
      leaf details {
        description
          "Human-readable description";
        type string {
          length "1..1024";
        }
      }
    }
  }

  augment "/ncs:devices/ncs:device/ncs:netconf-notifications/ncs:received-notifications/ncs:notification/ncs:data" {
    container escEvent {
      presence "";
      config false;
      uses ncs_rpc_notif_escevents;
    }
  }
}
