module esc_opdata_state_machines {
  // Generated by yanger -t ncs
  tailf:mount-id esc-nc-1.0:esc-nc-1.0;
  tailf:ncs-device-type "netconf";

  namespace "http://www.cisco.com/esc/esc_opdata_state_machines";
  prefix esc_opdata_state_machines;

  import esc_types {
    prefix types;
  }
  import "esc-nc-1.0" {
    prefix "esc-nc-1.0";
  }
  import tailf-ncs {
    prefix ncs;
  }
  import tailf-common {
    prefix tailf;
  }

  organization
    "Cisco Systems";
  contact
    "Elie El Ajaltouni <eelajalt@cisco.com>";

  revision 2014-09-22 {
    description
      "Elastic Services Controller Module's state machines operational data";
  }

  grouping ncs_template_esc_opdata_state_machines {
    description
      "This contains all the operational data of the service and VM
       state machines";
    container state_machine {
      leaf state {
        description
          "State in which service is currently in";
        type types:ncs_template_service_state_machine_states;
      }
      container vm_state_machines {
        list vm_state_machine {
          // NCS patched for predictable order
          ordered-by user;
          key "vm_name";
          leaf vm_name {
            description
              "Name uniquely identifies a VM";
            type string;
          }
          leaf state {
            description
              "State in which VM is currently in";
            type types:ncs_template_vm_state_machine_states;
          }
        }
      }
    }
  }

  grouping ncs_rpc_notif_esc_opdata_state_machines {
    description
      "This contains all the operational data of the service and VM
       state machines";
    container state_machine {
      leaf state {
        description
          "State in which service is currently in";
        type types:ncs_rpc_notif_service_state_machine_states;
      }
      container vm_state_machines {
        list vm_state_machine {
          key "vm_name";
          leaf vm_name {
            description
              "Name uniquely identifies a VM";
            type string;
          }
          leaf state {
            description
              "State in which VM is currently in";
            type types:ncs_rpc_notif_vm_state_machine_states;
          }
        }
      }
    }
  }

  grouping live_ncs_esc_opdata_state_machines {
    description
      "This contains all the operational data of the service and VM
       state machines";
    container state_machine {
      leaf state {
        description
          "State in which service is currently in";
        type types:live_ncs_service_state_machine_states;
      }
      container vm_state_machines {
        list vm_state_machine {
          key "vm_name";
          leaf vm_name {
            description
              "Name uniquely identifies a VM";
            type string;
          }
          leaf state {
            description
              "State in which VM is currently in";
            type types:live_ncs_vm_state_machine_states;
          }
        }
      }
    }
  }

  grouping esc_opdata_state_machines {
    description
      "This contains all the operational data of the service and VM
       state machines";
    container state_machine {
      leaf state {
        description
          "State in which service is currently in";
        type types:service_state_machine_states;
      }
      container vm_state_machines {
        list vm_state_machine {
          key "vm_name";
          leaf vm_name {
            description
              "Name uniquely identifies a VM";
            type string;
          }
          leaf state {
            description
              "State in which VM is currently in";
            type types:vm_state_machine_states;
          }
        }
      }
    }
  }
}
