module esc_disk {
  // Generated by yanger -t ncs
  tailf:mount-id esc-nc-1.0:esc-nc-1.0;
  tailf:ncs-device-type "netconf";

  namespace "http://www.cisco.com/esc/esc_disk";
  prefix esc_disk;

  import ietf-inet-types {
    prefix ietf-inet-types;
  }
  import esc_types {
    prefix types;
  }
  import esc_locators {
    prefix locators;
  }
  import tailf-common {
    prefix tailf;
  }
  import "esc-nc-1.0" {
    prefix "esc-nc-1.0";
  }
  import tailf-ncs {
    prefix ncs;
  }

  organization
    "Cisco Systems";
  contact
    "Shesha Sreenivasamurthy <shesha@cisco.com>";
  description
    "ESC's disk descriptions'";

  revision 2019-04-09 {
    description
      "Added new certificate fields to images";
  }
  revision 2019-02-20 {
    description
      "Added new checksum field to images";
  }
  revision 2018-10-17 {
    description
      "Adding remove_src_on_completion field to images";
  }
  revision 2018-07-24 {
    description
      "Grouping image properties for reuse";
  }
  revision 2016-07-14 {
    description
      "Added visibility string field to images";
  }
  revision 2016-03-16 {
    description
      "Added extensible locator to images";
  }
  revision 2015-08-18 {
    description
      "Remove image attribute 'public'";
  }
  revision 2015-06-29 {
    description
      "Datamodel change to support list of images";
  }
  revision 2015-06-04 {
    description
      "updated description";
  }
  revision 2014-06-23 {
    description
      "ESC Disk";
  }

  grouping ncs_template_disk_attributes {
    description
      "Disk properties are described in this section";
    leaf src {
      description
        "URL of the VM image from where it can be downloaded by ESC";
      type string;
      // NCS drop mandatory statement
    }
    leaf certificate_validation {
      description
        "Used to enable certificate validation on image registration";
      type string;
      // NCS drop default statement
    }
    choice certificate {
      case certificate_file {
        leaf certificate_file {
          description
            "Certificate file used to validate src downloads over https connections";
          type string;
        }
      }
      case certificate_string {
        leaf certificate_string {
          description
            "Certificate file content used to validate src downloads over https connections. MUST adhere to PEM standard";
          type string;
        }
      }
    }
    leaf size {
      description
        "Size of the image specified by URL above. If unsure, leave it blank";
      type string;
    }
    leaf sizeunit {
      description
        "Size unit. MiB/GiB/TiB/PiB/EiB";
      type types:ncs_template_szunits;
    }
    leaf disk_format {
      description
        "Format of the disk: qcow2, raw, vmdk";
      type types:ncs_template_disk_formats;
    }
    leaf container_format {
      description
        "";
      type string;
    }
    leaf serial_console {
      description
        "";
      type string;
    }
    leaf e1000_net {
      description
        "True if image has e1000 drivers";
      type string;
      // NCS drop default statement
    }
    leaf virtio_net {
      description
        "True if image has VIRTIO drivers";
      type string;
      // NCS drop default statement
    }
    leaf disk_bus {
      description
        "Root disk bus: ide, scsi, virtio";
      type types:ncs_template_iobus;
    }
    leaf visibility {
      description
        "Specifies whether image should be created as public or private";
      type string;
      // NCS drop default statement
    }
    container properties {
      uses ncs_template_image_properties;
    }
  }

  grouping ncs_template_image_properties {
    list property {
      // NCS patched for predictable order
      ordered-by user;
      key "name";
      description
        "Storage location for additional Image properties.";
      leaf name {
        description
          "Property key, for example maximum VCPUs supported by this VNF image.";
        type string;
        // NCS drop mandatory statement
      }
      leaf type {
        description
          "Type of property.";
        type string;
      }
      leaf-list value {
        // NCS patched for predictable order
        ordered-by user;
        description
          "One or more values";
        type string;
      }
    }
  }

  grouping ncs_template_esc_disk {
    container disk {
      uses ncs_template_disk_attributes;
    }
  }

  grouping ncs_template_esc_images {
    container images {
      list image {
        // NCS patched for predictable order
        ordered-by user;
        description
          "List of images";
        key "name";
        leaf name {
          description
            "Name of the image";
          type types:ncs_template_escname;
          // NCS drop mandatory statement
        }
        uses ncs_template_disk_attributes;
        leaf remove_src_on_completion {
          description
            "TRUE if image source file should be deleted after image registration is complete.";
          type string;
          // NCS drop default statement
        }
        leaf checksum {
          type string;
          description
            "SHA checksum for the file";
        }
        leaf checksum_algorithm {
          type types:ncs_template_checksum_type;
          description
            "Algorithm to use to validate the provided checksum";
          // NCS drop default statement
        }
        uses locators:ncs_template_extensible_locators;
        uses locators:ncs_template_locators;
      }
    }
  }

  grouping ncs_rpc_notif_disk_attributes {
    description
      "Disk properties are described in this section";
    leaf src {
      description
        "URL of the VM image from where it can be downloaded by ESC";
      type ietf-inet-types:uri;
      mandatory true;
    }
    leaf certificate_validation {
      description
        "Used to enable certificate validation on image registration";
      type boolean;
      default "false";
    }
    choice certificate {
      case certificate_file {
        leaf certificate_file {
          description
            "Certificate file used to validate src downloads over https connections";
          type ietf-inet-types:uri;
        }
      }
      case certificate_string {
        leaf certificate_string {
          description
            "Certificate file content used to validate src downloads over https connections. MUST adhere to PEM standard";
          type tailf:aes-cfb-128-encrypted-string;
        }
      }
    }
    leaf size {
      description
        "Size of the image specified by URL above. If unsure, leave it blank";
      type int32;
    }
    leaf sizeunit {
      description
        "Size unit. MiB/GiB/TiB/PiB/EiB";
      type types:ncs_rpc_notif_szunits;
    }
    leaf disk_format {
      description
        "Format of the disk: qcow2, raw, vmdk";
      type types:ncs_rpc_notif_disk_formats;
    }
    leaf container_format {
      description
        "";
      type string;
    }
    leaf serial_console {
      description
        "";
      type boolean;
    }
    leaf e1000_net {
      description
        "True if image has e1000 drivers";
      type boolean;
      default "false";
    }
    leaf virtio_net {
      description
        "True if image has VIRTIO drivers";
      type boolean;
      default "true";
    }
    leaf disk_bus {
      description
        "Root disk bus: ide, scsi, virtio";
      type types:ncs_rpc_notif_iobus;
    }
    leaf visibility {
      description
        "Specifies whether image should be created as public or private";
      type string;
      default "public";
    }
    container properties {
      uses ncs_rpc_notif_image_properties;
    }
  }

  grouping ncs_rpc_notif_image_properties {
    list property {
      key "name";
      description
        "Storage location for additional Image properties.";
      leaf name {
        description
          "Property key, for example maximum VCPUs supported by this VNF image.";
        type string;
        mandatory true;
      }
      leaf type {
        description
          "Type of property.";
        type string;
      }
      leaf-list value {
        description
          "One or more values";
        type string;
      }
    }
  }

  grouping ncs_rpc_notif_esc_disk {
    container disk {
      uses ncs_rpc_notif_disk_attributes;
    }
  }

  grouping ncs_rpc_notif_esc_images {
    container images {
      list image {
        description
          "List of images";
        key "name";
        leaf name {
          description
            "Name of the image";
          type types:ncs_rpc_notif_escname;
          mandatory true;
        }
        uses ncs_rpc_notif_disk_attributes;
        leaf remove_src_on_completion {
          description
            "TRUE if image source file should be deleted after image registration is complete.";
          type boolean;
          default "false";
        }
        leaf checksum {
          type string {
            pattern '([0-9a-fA-F])*';
          }
          description
            "SHA checksum for the file";
        }
        leaf checksum_algorithm {
          type types:ncs_rpc_notif_checksum_type;
          description
            "Algorithm to use to validate the provided checksum";
          default "sha256sum";
        }
        uses locators:ncs_rpc_notif_extensible_locators;
        uses locators:ncs_rpc_notif_locators;
      }
    }
  }

  grouping live_ncs_disk_attributes {
    description
      "Disk properties are described in this section";
    leaf src {
      description
        "URL of the VM image from where it can be downloaded by ESC";
      type ietf-inet-types:uri;
      // NCS drop mandatory statement
    }
    leaf certificate_validation {
      description
        "Used to enable certificate validation on image registration";
      type boolean;
      // NCS drop default statement
    }
    choice certificate {
      case certificate_file {
        leaf certificate_file {
          description
            "Certificate file used to validate src downloads over https connections";
          type ietf-inet-types:uri;
        }
      }
      case certificate_string {
        leaf certificate_string {
          description
            "Certificate file content used to validate src downloads over https connections. MUST adhere to PEM standard";
          type tailf:aes-cfb-128-encrypted-string;
        }
      }
    }
    leaf size {
      description
        "Size of the image specified by URL above. If unsure, leave it blank";
      type int32;
    }
    leaf sizeunit {
      description
        "Size unit. MiB/GiB/TiB/PiB/EiB";
      type types:live_ncs_szunits;
    }
    leaf disk_format {
      description
        "Format of the disk: qcow2, raw, vmdk";
      type types:live_ncs_disk_formats;
    }
    leaf container_format {
      description
        "";
      type string;
    }
    leaf serial_console {
      description
        "";
      type boolean;
    }
    leaf e1000_net {
      description
        "True if image has e1000 drivers";
      type boolean;
      // NCS drop default statement
    }
    leaf virtio_net {
      description
        "True if image has VIRTIO drivers";
      type boolean;
      // NCS drop default statement
    }
    leaf disk_bus {
      description
        "Root disk bus: ide, scsi, virtio";
      type types:live_ncs_iobus;
    }
    leaf visibility {
      description
        "Specifies whether image should be created as public or private";
      type string;
      // NCS drop default statement
    }
    container properties {
      uses live_ncs_image_properties;
    }
  }

  grouping live_ncs_image_properties {
    list property {
      key "name";
      description
        "Storage location for additional Image properties.";
      leaf name {
        description
          "Property key, for example maximum VCPUs supported by this VNF image.";
        type string;
        // NCS drop mandatory statement
      }
      leaf type {
        description
          "Type of property.";
        type string;
      }
      leaf-list value {
        description
          "One or more values";
        type string;
      }
    }
  }

  grouping live_ncs_esc_disk {
    container disk {
      uses live_ncs_disk_attributes;
    }
  }

  grouping live_ncs_esc_images {
    container images {
      list image {
        description
          "List of images";
        key "name";
        leaf name {
          description
            "Name of the image";
          type types:live_ncs_escname;
          // NCS drop mandatory statement
        }
        uses live_ncs_disk_attributes;
        leaf remove_src_on_completion {
          description
            "TRUE if image source file should be deleted after image registration is complete.";
          type boolean;
          // NCS drop default statement
        }
        leaf checksum {
          type string {
            pattern '([0-9a-fA-F])*';
          }
          description
            "SHA checksum for the file";
        }
        leaf checksum_algorithm {
          type types:live_ncs_checksum_type;
          description
            "Algorithm to use to validate the provided checksum";
          // NCS drop default statement
        }
        uses locators:live_ncs_extensible_locators;
        uses locators:live_ncs_locators;
      }
    }
  }

  grouping disk_attributes {
    description
      "Disk properties are described in this section";
    leaf src {
      description
        "URL of the VM image from where it can be downloaded by ESC";
      type ietf-inet-types:uri;
      mandatory true;
    }
    leaf certificate_validation {
      description
        "Used to enable certificate validation on image registration";
      type boolean;
      default "false";
    }
    choice certificate {
      case certificate_file {
        leaf certificate_file {
          description
            "Certificate file used to validate src downloads over https connections";
          type ietf-inet-types:uri;
        }
      }
      case certificate_string {
        leaf certificate_string {
          tailf:ned-ignore-compare-config;
          description
            "Certificate file content used to validate src downloads over https connections. MUST adhere to PEM standard";
          type tailf:aes-cfb-128-encrypted-string;
        }
      }
    }
    leaf size {
      description
        "Size of the image specified by URL above. If unsure, leave it blank";
      type int32;
    }
    leaf sizeunit {
      description
        "Size unit. MiB/GiB/TiB/PiB/EiB";
      type types:szunits;
    }
    leaf disk_format {
      description
        "Format of the disk: qcow2, raw, vmdk";
      type types:disk_formats;
    }
    leaf container_format {
      description
        "";
      type string;
    }
    leaf serial_console {
      description
        "";
      type boolean;
    }
    leaf e1000_net {
      description
        "True if image has e1000 drivers";
      type boolean;
      default "false";
    }
    leaf virtio_net {
      description
        "True if image has VIRTIO drivers";
      type boolean;
      default "true";
    }
    leaf disk_bus {
      description
        "Root disk bus: ide, scsi, virtio";
      type types:iobus;
    }
    leaf visibility {
      description
        "Specifies whether image should be created as public or private";
      type string;
      default "public";
    }
    container properties {
      uses image_properties;
    }
  }

  grouping image_properties {
    list property {
      key "name";
      description
        "Storage location for additional Image properties.";
      leaf name {
        description
          "Property key, for example maximum VCPUs supported by this VNF image.";
        type string;
        mandatory true;
      }
      leaf type {
        description
          "Type of property.";
        type string;
      }
      leaf-list value {
        description
          "One or more values";
        type string;
      }
    }
  }

  grouping esc_disk {
    container disk {
      uses disk_attributes;
    }
  }

  grouping esc_images {
    container images {
      list image {
        description
          "List of images";
        key "name";
        leaf name {
          description
            "Name of the image";
          type types:escname;
          mandatory true;
        }
        uses disk_attributes;
        leaf remove_src_on_completion {
          description
            "TRUE if image source file should be deleted after image registration is complete.";
          type boolean;
          default "false";
        }
        leaf checksum {
          type string {
            pattern '([0-9a-fA-F])*';
          }
          description
            "SHA checksum for the file";
        }
        leaf checksum_algorithm {
          type types:checksum_type;
          description
            "Algorithm to use to validate the provided checksum";
          default "sha256sum";
        }
        uses locators:extensible_locators;
        uses locators:locators;
      }
    }
  }
}
