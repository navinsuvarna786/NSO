module esc_property {
  // Generated by yanger -t ncs
  tailf:mount-id esc-nc-1.0:esc-nc-1.0;
  tailf:ncs-device-type "netconf";

  namespace "http://www.cisco.com/esc_property";
  prefix esc_property;

  import tailf-common {
    prefix tailf;
  }
  import "esc-nc-1.0" {
    prefix "esc-nc-1.0";
  }
  import tailf-ncs {
    prefix ncs;
  }

  organization
    "Cisco Systems";
  contact
    "Elie El Ajaltouni <eelajalt@cisco.com>";

  revision 2017-09-01 {
    description
      "Adding encryted_value for keeping secrets.";
  }

  grouping ncs_template_property_list_definition {
    container properties {
      description
        "List of property name/value pairs";
      list property {
        // NCS patched for predictable order
        ordered-by user;
        key "name";
        leaf name {
          description
            "Name/Key of property";
          type string;
        }
        choice value_type {
          leaf value {
            description
              "Value of property";
            type string;
          }
          leaf encrypted_value {
            description
              "Encrypted value of property";
            type string;
          }
        }
      }
    }
  }

  grouping ncs_rpc_notif_property_list_definition {
    container properties {
      description
        "List of property name/value pairs";
      list property {
        key "name";
        leaf name {
          description
            "Name/Key of property";
          type string;
        }
        choice value_type {
          leaf value {
            description
              "Value of property";
            type string;
          }
          leaf encrypted_value {
            description
              "Encrypted value of property";
            type tailf:aes-cfb-128-encrypted-string;
          }
        }
      }
    }
  }

  grouping live_ncs_property_list_definition {
    container properties {
      description
        "List of property name/value pairs";
      list property {
        key "name";
        leaf name {
          description
            "Name/Key of property";
          type string;
        }
        choice value_type {
          leaf value {
            description
              "Value of property";
            type string;
          }
          leaf encrypted_value {
            description
              "Encrypted value of property";
            type tailf:aes-cfb-128-encrypted-string;
          }
        }
      }
    }
  }

  grouping property_list_definition {
    container properties {
      description
        "List of property name/value pairs";
      list property {
        key "name";
        leaf name {
          description
            "Name/Key of property";
          type string;
        }
        choice value_type {
          leaf value {
            description
              "Value of property";
            type string;
          }
          leaf encrypted_value {
            tailf:ned-ignore-compare-config;
            description
              "Encrypted value of property";
            type tailf:aes-cfb-128-encrypted-string;
          }
        }
      }
    }
  }
}
