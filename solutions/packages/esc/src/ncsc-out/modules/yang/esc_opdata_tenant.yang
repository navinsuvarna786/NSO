module esc_opdata_tenant {
  // Generated by yanger -t ncs
  tailf:mount-id esc-nc-1.0:esc-nc-1.0;
  tailf:ncs-device-type "netconf";

  namespace "http://www.cisco.com/esc/esc_opdata_tenant";
  prefix esc_opdata_tenant;

  import esc_opdata_interface {
    prefix opinterface;
  }
  import esc_opdata_volumes {
    prefix opvolumes;
  }
  import esc_opdata_networks {
    prefix opnetworks;
  }
  import esc_opdata_state_machines {
    prefix opstatemachines;
  }
  import ietf-yang-types {
    prefix ietf-yang-types;
  }
  import tailf-common {
    prefix tailf;
  }
  import esc_types {
    prefix types;
  }
  import "esc-nc-1.0" {
    prefix "esc-nc-1.0";
  }
  import tailf-ncs {
    prefix ncs;
  }

  organization
    "Cisco Systems";
  contact
    "Shesha Sreenivasamurthy <shesha@cisco.com>";

  revision 2020-02-14 {
    description
      "Added supported_export_type element to vm_group";
  }
  revision 2018-09-25 {
    description
      "Added vm_restore container element";
  }
  revision 2018-07-05 {
    description
      "Add vdc field under vm_instance";
  }
  revision 2018-05-30 {
    description
      "Add image and flavor fields under vm group";
  }
  revision 2018-02-07 {
    description
      "Add generated name field under vm_instance";
  }
  revision 2017-05-01 {
    description
      "Rename esc tenant attribute multi_vim to vim_mapping";
  }
  revision 2017-03-27 {
    description
      "Added target VIM operational data per VM instance.";
  }
  revision 2017-03-13 {
    description
      "Removed references to service name, version and id";
  }
  revision 2017-03-06 {
    description
      "Add multi_vim attribute to tenant.";
  }
  revision 2017-03-01 {
    description
      "Added tenant volumes operational data under tenants.";
  }
  revision 2015-11-18 {
    description
      "Added volumes operational data to VMs.";
  }
  revision 2014-08-06 {
    description
      "Elastic Services Controller Module's tenant operational data";
  }

  grouping ncs_template_esc_opdata_tenant {
    description
      "This contains all the operational data of the services that
       have been registered and/or instantiated";
    container tenants {
      presence "Indicates that the service is running";
      list tenant {
        // NCS patched for predictable order
        ordered-by user;
        key "name";
        description
          "List of tenants";
        leaf name {
          type types:ncs_template_escname;
        }
        leaf tenant_id {
          description
            "External tenant ID for the tenant";
          type string;
        }
        leaf vim_mapping {
          description
            "Attribute to specify if the tenant is an esc tenant or if it is
             mapped to a vim tenant";
          type string;
        }
        uses opnetworks:ncs_template_esc_opdata_networks;
        uses opvolumes:ncs_template_esc_opdata_tenant_volumes;
        list deployments {
          // NCS patched for predictable order
          ordered-by user;
          key "deployment_name";
          description
            "List of deployments";
          leaf deployment_name {
            description
              "Name of the deployment";
            type types:ncs_template_escname;
          }
          leaf deployment_id {
            description
              "Internal Deployment ID for the service";
            type string;
          }
          list vm_group {
            // NCS patched for predictable order
            ordered-by user;
            key "name";
            leaf name {
              description
                "Group Name";
              type types:ncs_template_escname;
            }
            leaf flavor {
              description
                "Flavor";
              type types:ncs_template_escname;
            }
            leaf image {
              description
                "Image";
              type types:ncs_template_escname;
            }
            leaf bootup_time {
              description
                "Time in seconds that this VM takes to perform a cold boot. This will
                 be the time that ESC waits before deciding that the VM is
                 un-bootable.";
              type string;
            }
            leaf supported_export_type {
              description
                "The type of export that this VM can support. Values include
                 'none', 'cold' and 'live'";
              type string;
            }
            list vm_instance {
              // NCS patched for predictable order
              ordered-by user;
              description
                "List of running VMs in this group";
              key "vm_id";
              leaf name {
                description
                  "A name of the VM";
                type types:ncs_template_escname;
              }
              leaf generated_name {
                description
                  "ESC generated name of the VM";
                type types:ncs_template_escname;
              }
              leaf vm_id {
                description
                  "UUID of the VM";
                type string;
              }
              leaf vim_id {
                description
                  "ESC defined id of the VIM where this VM is deployed";
                type types:ncs_template_escname;
              }
              leaf vim_project {
                description
                  "Name of the target project";
                type string;
              }
              leaf vim_project_id {
                description
                  "External ID for the project";
                type string;
              }
              leaf host_id {
                description
                  "ID of the host where this VM is running";
                type string;
              }
              leaf hostname {
                description
                  "Hostname where this VM is running. This is sometimes
                   referred to a hypervisor name.";
                type string;
                tailf:code-name "esc_hostname";
              }
              leaf vdc {
                description
                  "VMware vCloud Director org virtual data center.";
                type string;
              }
              leaf software_version {
                description
                  "Software version of the VM";
                type types:ncs_template_escname;
              }
              container vm_restore {
                description
                  "Details of the VM backup source archive used for this deployment";
                leaf vm_restored_from {
                  description
                    "path to backup archive used for this VM instance deployment";
                  type string;
                }
              }
              uses opinterface:ncs_template_esc_opdata_interface;
              uses opvolumes:ncs_template_esc_opdata_deployment_volumes;
            }
            list shared_ip {
              // NCS patched for predictable order
              ordered-by user;
              description
                "Shared Ip is the ip address that is shared by all the VM
                 in the vm_group on a particular nicid";
              key "nicid";
              leaf nicid {
                description
                  "Interface where the static_ip property is applied.";
                type string;
                // NCS drop mandatory statement
              }
              leaf ip_address {
                description
                  "shared IP address for this interface";
                type types:ncs_template_escipaddr;
              }
            }
          }
          uses opstatemachines:ncs_template_esc_opdata_state_machines;
        }
      }
    }
  }

  grouping ncs_rpc_notif_esc_opdata_tenant {
    description
      "This contains all the operational data of the services that
       have been registered and/or instantiated";
    container tenants {
      presence "Indicates that the service is running";
      list tenant {
        key "name";
        description
          "List of tenants";
        leaf name {
          type types:ncs_rpc_notif_escname;
        }
        leaf tenant_id {
          description
            "External tenant ID for the tenant";
          type string;
        }
        leaf vim_mapping {
          description
            "Attribute to specify if the tenant is an esc tenant or if it is
             mapped to a vim tenant";
          type boolean;
        }
        uses opnetworks:ncs_rpc_notif_esc_opdata_networks;
        uses opvolumes:ncs_rpc_notif_esc_opdata_tenant_volumes;
        list deployments {
          key "deployment_name";
          description
            "List of deployments";
          leaf deployment_name {
            description
              "Name of the deployment";
            type types:ncs_rpc_notif_escname;
          }
          leaf deployment_id {
            description
              "Internal Deployment ID for the service";
            type string;
          }
          list vm_group {
            key "name";
            leaf name {
              description
                "Group Name";
              type types:ncs_rpc_notif_escname;
            }
            leaf flavor {
              description
                "Flavor";
              type types:ncs_rpc_notif_escname;
            }
            leaf image {
              description
                "Image";
              type types:ncs_rpc_notif_escname;
            }
            leaf bootup_time {
              description
                "Time in seconds that this VM takes to perform a cold boot. This will
                 be the time that ESC waits before deciding that the VM is
                 un-bootable.";
              type int32;
            }
            leaf supported_export_type {
              description
                "The type of export that this VM can support. Values include
                 'none', 'cold' and 'live'";
              type enumeration {
                enum "none" {
                  description
                    "VM does not support any kind of export action";
                }
                enum "cold" {
                  description
                    "VM only supports export if VM is shut down first";
                }
                enum "live" {
                  description
                    "VM can be exported with or without shutting down";
                }
              }
            }
            list vm_instance {
              description
                "List of running VMs in this group";
              key "vm_id";
              leaf name {
                description
                  "A name of the VM";
                type types:ncs_rpc_notif_escname;
              }
              leaf generated_name {
                description
                  "ESC generated name of the VM";
                type types:ncs_rpc_notif_escname;
              }
              leaf vm_id {
                description
                  "UUID of the VM";
                type ietf-yang-types:uuid;
              }
              leaf vim_id {
                description
                  "ESC defined id of the VIM where this VM is deployed";
                type types:ncs_rpc_notif_escname;
              }
              leaf vim_project {
                description
                  "Name of the target project";
                type string;
              }
              leaf vim_project_id {
                description
                  "External ID for the project";
                type string;
              }
              leaf host_id {
                description
                  "ID of the host where this VM is running";
                type string;
              }
              leaf hostname {
                description
                  "Hostname where this VM is running. This is sometimes
                   referred to a hypervisor name.";
                type string;
                tailf:code-name "esc_hostname";
              }
              leaf vdc {
                description
                  "VMware vCloud Director org virtual data center.";
                type string;
              }
              leaf software_version {
                description
                  "Software version of the VM";
                type types:ncs_rpc_notif_escname;
              }
              container vm_restore {
                description
                  "Details of the VM backup source archive used for this deployment";
                leaf vm_restored_from {
                  description
                    "path to backup archive used for this VM instance deployment";
                  type string;
                }
              }
              uses opinterface:ncs_rpc_notif_esc_opdata_interface;
              uses opvolumes:ncs_rpc_notif_esc_opdata_deployment_volumes;
            }
            list shared_ip {
              description
                "Shared Ip is the ip address that is shared by all the VM
                 in the vm_group on a particular nicid";
              key "nicid";
              leaf nicid {
                description
                  "Interface where the static_ip property is applied.";
                type uint16;
                mandatory true;
              }
              leaf ip_address {
                description
                  "shared IP address for this interface";
                type types:ncs_rpc_notif_escipaddr;
              }
            }
          }
          uses opstatemachines:ncs_rpc_notif_esc_opdata_state_machines;
        }
      }
    }
  }

  grouping live_ncs_esc_opdata_tenant {
    description
      "This contains all the operational data of the services that
       have been registered and/or instantiated";
    container tenants {
      presence "Indicates that the service is running";
      list tenant {
        key "name";
        description
          "List of tenants";
        leaf name {
          type types:live_ncs_escname;
        }
        leaf tenant_id {
          description
            "External tenant ID for the tenant";
          type string;
        }
        leaf vim_mapping {
          description
            "Attribute to specify if the tenant is an esc tenant or if it is
             mapped to a vim tenant";
          type boolean;
        }
        uses opnetworks:live_ncs_esc_opdata_networks;
        uses opvolumes:live_ncs_esc_opdata_tenant_volumes;
        list deployments {
          key "deployment_name";
          description
            "List of deployments";
          leaf deployment_name {
            description
              "Name of the deployment";
            type types:live_ncs_escname;
          }
          leaf deployment_id {
            description
              "Internal Deployment ID for the service";
            type string;
          }
          list vm_group {
            key "name";
            leaf name {
              description
                "Group Name";
              type types:live_ncs_escname;
            }
            leaf flavor {
              description
                "Flavor";
              type types:live_ncs_escname;
            }
            leaf image {
              description
                "Image";
              type types:live_ncs_escname;
            }
            leaf bootup_time {
              description
                "Time in seconds that this VM takes to perform a cold boot. This will
                 be the time that ESC waits before deciding that the VM is
                 un-bootable.";
              type int32;
            }
            leaf supported_export_type {
              description
                "The type of export that this VM can support. Values include
                 'none', 'cold' and 'live'";
              type enumeration {
                enum "none" {
                  description
                    "VM does not support any kind of export action";
                }
                enum "cold" {
                  description
                    "VM only supports export if VM is shut down first";
                }
                enum "live" {
                  description
                    "VM can be exported with or without shutting down";
                }
              }
            }
            list vm_instance {
              description
                "List of running VMs in this group";
              key "vm_id";
              leaf name {
                description
                  "A name of the VM";
                type types:live_ncs_escname;
              }
              leaf generated_name {
                description
                  "ESC generated name of the VM";
                type types:live_ncs_escname;
              }
              leaf vm_id {
                description
                  "UUID of the VM";
                type ietf-yang-types:uuid;
              }
              leaf vim_id {
                description
                  "ESC defined id of the VIM where this VM is deployed";
                type types:live_ncs_escname;
              }
              leaf vim_project {
                description
                  "Name of the target project";
                type string;
              }
              leaf vim_project_id {
                description
                  "External ID for the project";
                type string;
              }
              leaf host_id {
                description
                  "ID of the host where this VM is running";
                type string;
              }
              leaf hostname {
                description
                  "Hostname where this VM is running. This is sometimes
                   referred to a hypervisor name.";
                type string;
                tailf:code-name "esc_hostname";
              }
              leaf vdc {
                description
                  "VMware vCloud Director org virtual data center.";
                type string;
              }
              leaf software_version {
                description
                  "Software version of the VM";
                type types:live_ncs_escname;
              }
              container vm_restore {
                description
                  "Details of the VM backup source archive used for this deployment";
                leaf vm_restored_from {
                  description
                    "path to backup archive used for this VM instance deployment";
                  type string;
                }
              }
              uses opinterface:live_ncs_esc_opdata_interface;
              uses opvolumes:live_ncs_esc_opdata_deployment_volumes;
            }
            list shared_ip {
              description
                "Shared Ip is the ip address that is shared by all the VM
                 in the vm_group on a particular nicid";
              key "nicid";
              leaf nicid {
                description
                  "Interface where the static_ip property is applied.";
                type uint16;
                // NCS drop mandatory statement
              }
              leaf ip_address {
                description
                  "shared IP address for this interface";
                type types:live_ncs_escipaddr;
              }
            }
          }
          uses opstatemachines:live_ncs_esc_opdata_state_machines;
        }
      }
    }
  }

  grouping esc_opdata_tenant {
    description
      "This contains all the operational data of the services that
       have been registered and/or instantiated";
    container tenants {
      presence "Indicates that the service is running";
      list tenant {
        key "name";
        description
          "List of tenants";
        leaf name {
          type types:escname;
        }
        leaf tenant_id {
          description
            "External tenant ID for the tenant";
          type string;
        }
        leaf vim_mapping {
          description
            "Attribute to specify if the tenant is an esc tenant or if it is
             mapped to a vim tenant";
          type boolean;
        }
        uses opnetworks:esc_opdata_networks;
        uses opvolumes:esc_opdata_tenant_volumes;
        list deployments {
          key "deployment_name";
          description
            "List of deployments";
          leaf deployment_name {
            description
              "Name of the deployment";
            type types:escname;
          }
          leaf deployment_id {
            description
              "Internal Deployment ID for the service";
            type string;
          }
          list vm_group {
            key "name";
            leaf name {
              description
                "Group Name";
              type types:escname;
            }
            leaf flavor {
              description
                "Flavor";
              type types:escname;
            }
            leaf image {
              description
                "Image";
              type types:escname;
            }
            leaf bootup_time {
              description
                "Time in seconds that this VM takes to perform a cold boot. This will
                 be the time that ESC waits before deciding that the VM is
                 un-bootable.";
              type int32;
            }
            leaf supported_export_type {
              description
                "The type of export that this VM can support. Values include
                 'none', 'cold' and 'live'";
              type enumeration {
                enum "none" {
                  description
                    "VM does not support any kind of export action";
                }
                enum "cold" {
                  description
                    "VM only supports export if VM is shut down first";
                }
                enum "live" {
                  description
                    "VM can be exported with or without shutting down";
                }
              }
            }
            list vm_instance {
              description
                "List of running VMs in this group";
              key "vm_id";
              leaf name {
                description
                  "A name of the VM";
                type types:escname;
              }
              leaf generated_name {
                description
                  "ESC generated name of the VM";
                type types:escname;
              }
              leaf vm_id {
                description
                  "UUID of the VM";
                type ietf-yang-types:uuid;
              }
              leaf vim_id {
                description
                  "ESC defined id of the VIM where this VM is deployed";
                type types:escname;
              }
              leaf vim_project {
                description
                  "Name of the target project";
                type string;
              }
              leaf vim_project_id {
                description
                  "External ID for the project";
                type string;
              }
              leaf host_id {
                description
                  "ID of the host where this VM is running";
                type string;
              }
              leaf hostname {
                description
                  "Hostname where this VM is running. This is sometimes
                   referred to a hypervisor name.";
                type string;
                tailf:code-name "esc_hostname";
              }
              leaf vdc {
                description
                  "VMware vCloud Director org virtual data center.";
                type string;
              }
              leaf software_version {
                description
                  "Software version of the VM";
                type types:escname;
              }
              container vm_restore {
                description
                  "Details of the VM backup source archive used for this deployment";
                leaf vm_restored_from {
                  description
                    "path to backup archive used for this VM instance deployment";
                  type string;
                }
              }
              uses opinterface:esc_opdata_interface;
              uses opvolumes:esc_opdata_deployment_volumes;
            }
            list shared_ip {
              description
                "Shared Ip is the ip address that is shared by all the VM
                 in the vm_group on a particular nicid";
              key "nicid";
              leaf nicid {
                description
                  "Interface where the static_ip property is applied.";
                type uint16;
                mandatory true;
              }
              leaf ip_address {
                description
                  "shared IP address for this interface";
                type types:escipaddr;
              }
            }
          }
          uses opstatemachines:esc_opdata_state_machines;
        }
      }
    }
  }
}
