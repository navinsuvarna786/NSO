module esc-nc-1.0 {
  yang-version 1.1;
  namespace "http://tail-f.com/ns/ned-id/esc-nc-1.0";
  prefix esc-nc-1.0;

  import esc-nc {
    prefix family;
  }

  identity esc-nc-1.0 {
    base family:esc-nc;
  }
}
