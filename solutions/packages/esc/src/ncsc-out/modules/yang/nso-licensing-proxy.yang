module nso-licensing-proxy {
  // Generated by yanger -t ncs
  tailf:mount-id esc-nc-1.0:esc-nc-1.0;
  tailf:ncs-device-type "netconf";

  namespace "http://cisco.com/yang/nso/licensing-proxy";
  prefix licensing-proxy;

  import "esc-nc-1.0" {
    prefix "esc-nc-1.0";
  }
  import tailf-ncs {
    prefix ncs;
  }
  import tailf-common {
    prefix tailf;
  }

  revision 2018-10-25 {
    description
      "Added smart licensing";
  }

  augment "/ncs:devices/ncs:device/ncs:netconf-notifications/ncs:received-notifications/ncs:notification/ncs:data" {
    container nso-licensing-proxy {
      presence "";
      config false;
      description
        "NSO licensing notification";
      leaf unique-id {
        type string;
      }
      list entitlement {
        key "id";
        leaf id {
          type string;
        }
        leaf n {
          type uint64;
        }
      }
    }
  }
}
