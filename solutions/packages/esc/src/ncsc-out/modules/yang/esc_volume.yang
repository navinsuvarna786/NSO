module esc_volume {
  // Generated by yanger -t ncs
  tailf:mount-id esc-nc-1.0:esc-nc-1.0;
  tailf:ncs-device-type "netconf";

  namespace "http://www.cisco.com/esc/esc_volume";
  prefix esc_volume;

  import esc_types {
    prefix types;
  }
  import "esc-nc-1.0" {
    prefix "esc-nc-1.0";
  }
  import tailf-ncs {
    prefix ncs;
  }
  import tailf-common {
    prefix tailf;
  }

  organization
    "Cisco Systems";
  contact
    "Shesha Sreenivasamurthy <shesha@cisco.com>";
  description
    "ESC's volume descriptions'";

  revision 2017-03-09 {
    description
      "Modified tenant_volume to use only the necessary info.";
  }
  revision 2017-02-27 {
    description
      "Added tenant_volume to support the volume API.";
  }
  revision 2016-03-18 {
    description
      "Added image leaf to volume list.";
  }
  revision 2016-01-13 {
    description
      "Added boot_index to Volume list.";
  }
  revision 2015-11-18 {
    description
      "Added volid as another key to Volume list.";
  }
  revision 2015-11-09 {
    description
      "Added support for volume_type";
  }
  revision 2014-06-23 {
    description
      "ESC Volume";
  }

  grouping ncs_template_esc_volume_details {
    leaf size {
      description
        "Size of the Volume";
      type string;
    }
    leaf sizeunit {
      description
        "Size units. MiB/GiB/TiB/PiB/EiB";
      type types:ncs_template_szunits;
    }
    leaf image {
      description
        "Name or UUID of the source image";
      type string;
    }
    leaf type {
      description
        " Allows to provide scheduling to a specific back-end,
          and also can be used to specify specific information
          for a back-end storage device to act upon.";
      type types:ncs_template_escname;
    }
    leaf format {
      description
        " Format of the disk to create.";
      type types:ncs_template_disk_formats;
    }
    leaf device_type {
      description
        " Type of device being attached to the VM.";
      type types:ncs_template_device_type;
    }
    leaf storage_location {
      description
        " Location of the storage volume.";
      type string;
    }
  }

  grouping ncs_template_esc_tenant_volume {
    container volumes {
      description
        "This is for the Volume API to create a volume to later attach it to a VM if needed";
      list volume {
        // NCS patched for predictable order
        ordered-by user;
        key "name";
        leaf name {
          description
            "Name of the Volume";
          type types:ncs_template_escname;
          // NCS drop mandatory statement
        }
        uses ncs_template_esc_volume_details;
      }
    }
  }

  grouping ncs_template_esc_volume_deployment {
    container volumes {
      description
        "Volumes that are to be attached to the VM. The administrator can
         specify a range for volumes outside vm_group section and
         then specify xpath for the size here. This is enable the
         deployer to choose any size within a range during deployment.";
      list volume {
        // NCS patched for predictable order
        ordered-by user;
        key "name volid";
        leaf name {
          description
            "Name of the Volume";
          type types:ncs_template_escname;
          // NCS drop mandatory statement
        }
        leaf volid {
          description
            "Volumes will be presented to the VM sorted by volume ID";
          type string;
          // NCS drop mandatory statement
        }
        leaf bus {
          description
            "Block device bus to be used: ide, scsi, virtio";
          type types:ncs_template_iobus;
        }
        leaf boot_index {
          description
            "Specify the boot order for bootable volumes.";
          type string;
        }
        uses ncs_template_esc_volume_details;
      }
    }
  }

  grouping ncs_rpc_notif_esc_volume_details {
    leaf size {
      description
        "Size of the Volume";
      type uint16;
    }
    leaf sizeunit {
      description
        "Size units. MiB/GiB/TiB/PiB/EiB";
      type types:ncs_rpc_notif_szunits;
    }
    leaf image {
      description
        "Name or UUID of the source image";
      type string;
    }
    leaf type {
      description
        " Allows to provide scheduling to a specific back-end,
          and also can be used to specify specific information
          for a back-end storage device to act upon.";
      type types:ncs_rpc_notif_escname;
    }
    leaf format {
      description
        " Format of the disk to create.";
      type types:ncs_rpc_notif_disk_formats;
    }
    leaf device_type {
      description
        " Type of device being attached to the VM.";
      type types:ncs_rpc_notif_device_type;
    }
    leaf storage_location {
      description
        " Location of the storage volume.";
      type string;
    }
  }

  grouping ncs_rpc_notif_esc_tenant_volume {
    container volumes {
      description
        "This is for the Volume API to create a volume to later attach it to a VM if needed";
      list volume {
        key "name";
        leaf name {
          description
            "Name of the Volume";
          type types:ncs_rpc_notif_escname;
          mandatory true;
        }
        uses ncs_rpc_notif_esc_volume_details;
      }
    }
  }

  grouping ncs_rpc_notif_esc_volume_deployment {
    container volumes {
      description
        "Volumes that are to be attached to the VM. The administrator can
         specify a range for volumes outside vm_group section and
         then specify xpath for the size here. This is enable the
         deployer to choose any size within a range during deployment.";
      list volume {
        key "name volid";
        leaf name {
          description
            "Name of the Volume";
          type types:ncs_rpc_notif_escname;
          mandatory true;
        }
        leaf volid {
          description
            "Volumes will be presented to the VM sorted by volume ID";
          type uint16;
          mandatory true;
        }
        leaf bus {
          description
            "Block device bus to be used: ide, scsi, virtio";
          type types:ncs_rpc_notif_iobus;
        }
        leaf boot_index {
          description
            "Specify the boot order for bootable volumes.";
          type uint16;
        }
        uses ncs_rpc_notif_esc_volume_details;
      }
    }
  }

  grouping live_ncs_esc_volume_details {
    leaf size {
      description
        "Size of the Volume";
      type uint16;
    }
    leaf sizeunit {
      description
        "Size units. MiB/GiB/TiB/PiB/EiB";
      type types:live_ncs_szunits;
    }
    leaf image {
      description
        "Name or UUID of the source image";
      type string;
    }
    leaf type {
      description
        " Allows to provide scheduling to a specific back-end,
          and also can be used to specify specific information
          for a back-end storage device to act upon.";
      type types:live_ncs_escname;
    }
    leaf format {
      description
        " Format of the disk to create.";
      type types:live_ncs_disk_formats;
    }
    leaf device_type {
      description
        " Type of device being attached to the VM.";
      type types:live_ncs_device_type;
    }
    leaf storage_location {
      description
        " Location of the storage volume.";
      type string;
    }
  }

  grouping live_ncs_esc_tenant_volume {
    container volumes {
      description
        "This is for the Volume API to create a volume to later attach it to a VM if needed";
      list volume {
        key "name";
        leaf name {
          description
            "Name of the Volume";
          type types:live_ncs_escname;
          // NCS drop mandatory statement
        }
        uses live_ncs_esc_volume_details;
      }
    }
  }

  grouping live_ncs_esc_volume_deployment {
    container volumes {
      description
        "Volumes that are to be attached to the VM. The administrator can
         specify a range for volumes outside vm_group section and
         then specify xpath for the size here. This is enable the
         deployer to choose any size within a range during deployment.";
      list volume {
        key "name volid";
        leaf name {
          description
            "Name of the Volume";
          type types:live_ncs_escname;
          // NCS drop mandatory statement
        }
        leaf volid {
          description
            "Volumes will be presented to the VM sorted by volume ID";
          type uint16;
          // NCS drop mandatory statement
        }
        leaf bus {
          description
            "Block device bus to be used: ide, scsi, virtio";
          type types:live_ncs_iobus;
        }
        leaf boot_index {
          description
            "Specify the boot order for bootable volumes.";
          type uint16;
        }
        uses live_ncs_esc_volume_details;
      }
    }
  }

  grouping esc_volume_details {
    leaf size {
      description
        "Size of the Volume";
      type uint16;
    }
    leaf sizeunit {
      description
        "Size units. MiB/GiB/TiB/PiB/EiB";
      type types:szunits;
    }
    leaf image {
      description
        "Name or UUID of the source image";
      type string;
    }
    leaf type {
      description
        " Allows to provide scheduling to a specific back-end,
          and also can be used to specify specific information
          for a back-end storage device to act upon.";
      type types:escname;
    }
    leaf format {
      description
        " Format of the disk to create.";
      type types:disk_formats;
    }
    leaf device_type {
      description
        " Type of device being attached to the VM.";
      type types:device_type;
    }
    leaf storage_location {
      description
        " Location of the storage volume.";
      type string;
    }
  }

  grouping esc_tenant_volume {
    container volumes {
      description
        "This is for the Volume API to create a volume to later attach it to a VM if needed";
      list volume {
        key "name";
        leaf name {
          description
            "Name of the Volume";
          type types:escname;
          mandatory true;
        }
        uses esc_volume_details;
      }
    }
  }

  grouping esc_volume_deployment {
    container volumes {
      description
        "Volumes that are to be attached to the VM. The administrator can
         specify a range for volumes outside vm_group section and
         then specify xpath for the size here. This is enable the
         deployer to choose any size within a range during deployment.";
      list volume {
        key "name volid";
        leaf name {
          description
            "Name of the Volume";
          type types:escname;
          mandatory true;
        }
        leaf volid {
          description
            "Volumes will be presented to the VM sorted by volume ID";
          type uint16;
          mandatory true;
        }
        leaf bus {
          description
            "Block device bus to be used: ide, scsi, virtio";
          type types:iobus;
        }
        leaf boot_index {
          description
            "Specify the boot order for bootable volumes.";
          type uint16;
        }
        uses esc_volume_details;
      }
    }
  }
}
