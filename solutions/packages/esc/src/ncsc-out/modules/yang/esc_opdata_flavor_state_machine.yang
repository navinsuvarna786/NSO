module esc_opdata_flavor_state_machine {
  // Generated by yanger -t ncs
  tailf:mount-id esc-nc-1.0:esc-nc-1.0;
  tailf:ncs-device-type "netconf";

  namespace "http://www.cisco.com/esc/esc_opdata_flavor_state_machines";
  prefix esc_opdata_flavor_state_machine;

  import esc_types {
    prefix types;
  }
  import "esc-nc-1.0" {
    prefix "esc-nc-1.0";
  }
  import tailf-ncs {
    prefix ncs;
  }
  import tailf-common {
    prefix tailf;
  }

  organization
    "Cisco Systems";
  contact
    "Elie El Ajaltouni <eelajalt@cisco.com>";

  revision 2015-11-24 {
    description
      "Elastic Services Controller Module's flavor state machines operational data";
  }

  grouping ncs_template_esc_opdata_flavor_state_machine {
    description
      "This contains all the operational data of the flavor
       state machine";
    leaf flavor_name {
      description
        "Name uniquely identifies a Flavor";
      type string;
    }
    leaf state {
      description
        "State in which Flavor is currently in";
      type types:ncs_template_flavor_state_machine_states;
    }
  }

  grouping ncs_rpc_notif_esc_opdata_flavor_state_machine {
    description
      "This contains all the operational data of the flavor
       state machine";
    leaf flavor_name {
      description
        "Name uniquely identifies a Flavor";
      type string;
    }
    leaf state {
      description
        "State in which Flavor is currently in";
      type types:ncs_rpc_notif_flavor_state_machine_states;
    }
  }

  grouping live_ncs_esc_opdata_flavor_state_machine {
    description
      "This contains all the operational data of the flavor
       state machine";
    leaf flavor_name {
      description
        "Name uniquely identifies a Flavor";
      type string;
    }
    leaf state {
      description
        "State in which Flavor is currently in";
      type types:live_ncs_flavor_state_machine_states;
    }
  }

  grouping esc_opdata_flavor_state_machine {
    description
      "This contains all the operational data of the flavor
       state machine";
    leaf flavor_name {
      description
        "Name uniquely identifies a Flavor";
      type string;
    }
    leaf state {
      description
        "State in which Flavor is currently in";
      type types:flavor_state_machine_states;
    }
  }
}
