module esc_config_parameter {
  // Generated by yanger -t ncs
  tailf:mount-id esc-nc-1.0:esc-nc-1.0;
  tailf:ncs-device-type "netconf";

  namespace "http://www.cisco.com/esc/esc_config_parameter";
  prefix esc_config_parameter;

  import tailf-common {
    prefix tailf;
  }
  import esc_types {
    prefix types;
  }
  import "esc-nc-1.0" {
    prefix "esc-nc-1.0";
  }
  import tailf-ncs {
    prefix ncs;
  }

  organization
    "Cisco Systems";
  description
    "ESC Config parameters config";

  revision 2020-06-17 {
    description
      "ESC Config parameter config support";
  }

  grouping ncs_template_esc_config_parameter {
    container config_parameters {
      list config_parameter {
        // NCS patched for predictable order
        ordered-by user;
        key "category property";
        description
          "List of config parameters.";
        leaf category {
          description
            "Type of config param category: VAGRANT, OPENSTACK, NB, etc";
          type types:ncs_template_escname;
          // NCS drop mandatory statement
        }
        leaf property {
          description
            "A unique id to represent a VIM connection.";
          type types:ncs_template_escname;
          // NCS drop mandatory statement
        }
        leaf value {
          description
            "config property value to set.";
          type string;
          // NCS drop mandatory statement
        }
      }
    }
  }

  grouping ncs_rpc_notif_esc_config_parameter {
    container config_parameters {
      list config_parameter {
        key "category property";
        description
          "List of config parameters.";
        leaf category {
          description
            "Type of config param category: VAGRANT, OPENSTACK, NB, etc";
          tailf:cli-expose-key-name;
          type types:ncs_rpc_notif_escname;
          mandatory true;
        }
        leaf property {
          description
            "A unique id to represent a VIM connection.";
          tailf:cli-expose-key-name;
          type types:ncs_rpc_notif_escname;
          mandatory true;
        }
        leaf value {
          description
            "config property value to set.";
          type string;
          mandatory true;
        }
      }
    }
  }

  grouping live_ncs_esc_config_parameter {
    container config_parameters {
      list config_parameter {
        key "category property";
        description
          "List of config parameters.";
        leaf category {
          description
            "Type of config param category: VAGRANT, OPENSTACK, NB, etc";
          // NCS drop tailf:cli-expose-key-name
          type types:live_ncs_escname;
          // NCS drop mandatory statement
        }
        leaf property {
          description
            "A unique id to represent a VIM connection.";
          // NCS drop tailf:cli-expose-key-name
          type types:live_ncs_escname;
          // NCS drop mandatory statement
        }
        leaf value {
          description
            "config property value to set.";
          type string;
          // NCS drop mandatory statement
        }
      }
    }
  }

  grouping esc_config_parameter {
    container config_parameters {
      list config_parameter {
        key "category property";
        description
          "List of config parameters.";
        leaf category {
          description
            "Type of config param category: VAGRANT, OPENSTACK, NB, etc";
          tailf:cli-expose-key-name;
          type types:escname;
          mandatory true;
        }
        leaf property {
          description
            "A unique id to represent a VIM connection.";
          tailf:cli-expose-key-name;
          type types:escname;
          mandatory true;
        }
        leaf value {
          description
            "config property value to set.";
          type string;
          mandatory true;
        }
      }
    }
  }
}
