module esc_file_server {
  // Generated by yanger -t ncs
  tailf:mount-id esc-nc-1.0:esc-nc-1.0;
  tailf:ncs-device-type "netconf";

  namespace "http://www.cisco.com/esc/esc_file_server";
  prefix esc_file_server;

  import esc_types {
    prefix types;
  }
  import esc_property {
    prefix property;
  }
  import tailf-common {
    prefix tailf;
  }
  import ietf-inet-types {
    prefix ietf-inet-types;
  }
  import "esc-nc-1.0" {
    prefix "esc-nc-1.0";
  }
  import tailf-ncs {
    prefix ncs;
  }

  organization
    "Cisco Systems";
  description
    "File Server details";

  revision 2017-09-25 {
    description
      "defining file server configuration";
  }

  grouping ncs_template_esc_file_server {
    container file_servers {
      list file_server {
        // NCS patched for predictable order
        ordered-by user;
        key "id";
        description
          "List of file servers.";
        leaf id {
          description
            "A unique identifier name to represent a file server";
          type types:ncs_template_escname;
          // NCS drop mandatory statement
        }
        leaf base_url {
          description
            "URI for the server";
          type string;
          // NCS drop mandatory statement
        }
        leaf file_server_user {
          description
            "username credential for access to server";
          type types:ncs_template_escname;
        }
        leaf file_server_password {
          description
            "password for server access";
          type string;
        }
        uses property:ncs_template_property_list_definition;
      }
    }
  }

  grouping ncs_rpc_notif_esc_file_server {
    container file_servers {
      list file_server {
        key "id";
        description
          "List of file servers.";
        leaf id {
          description
            "A unique identifier name to represent a file server";
          type types:ncs_rpc_notif_escname;
          mandatory true;
        }
        leaf base_url {
          description
            "URI for the server";
          type ietf-inet-types:uri;
          mandatory true;
        }
        leaf file_server_user {
          description
            "username credential for access to server";
          type types:ncs_rpc_notif_escname;
        }
        leaf file_server_password {
          description
            "password for server access";
          type tailf:aes-cfb-128-encrypted-string;
        }
        uses property:ncs_rpc_notif_property_list_definition;
      }
    }
  }

  grouping live_ncs_esc_file_server {
    container file_servers {
      list file_server {
        key "id";
        description
          "List of file servers.";
        leaf id {
          description
            "A unique identifier name to represent a file server";
          type types:live_ncs_escname;
          // NCS drop mandatory statement
        }
        leaf base_url {
          description
            "URI for the server";
          type ietf-inet-types:uri;
          // NCS drop mandatory statement
        }
        leaf file_server_user {
          description
            "username credential for access to server";
          type types:live_ncs_escname;
        }
        leaf file_server_password {
          description
            "password for server access";
          type tailf:aes-cfb-128-encrypted-string;
        }
        uses property:live_ncs_property_list_definition;
      }
    }
  }

  grouping esc_file_server {
    container file_servers {
      list file_server {
        key "id";
        description
          "List of file servers.";
        leaf id {
          description
            "A unique identifier name to represent a file server";
          type types:escname;
          mandatory true;
        }
        leaf base_url {
          description
            "URI for the server";
          type ietf-inet-types:uri;
          mandatory true;
        }
        leaf file_server_user {
          description
            "username credential for access to server";
          type types:escname;
        }
        leaf file_server_password {
          tailf:ned-ignore-compare-config;
          description
            "password for server access";
          type tailf:aes-cfb-128-encrypted-string;
        }
        uses property:property_list_definition;
      }
    }
  }
}
