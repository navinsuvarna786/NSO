submodule esc_serial_ports {
  // Generated by yanger -t ncs
  tailf:mount-id esc-nc-1.0:esc-nc-1.0;

  belongs-to esc_datamodel {
    prefix serial_ports;
  }

  import "esc-nc-1.0" {
    prefix "esc-nc-1.0";
  }
  import tailf-ncs {
    prefix ncs;
  }
  import tailf-common {
    prefix tailf;
  }

  organization
    "Cisco Systems";
  contact
    "Shesha Sreenivasamurthy <shesha@cisco.com>";
  description
    "ESC's serial port descriptions'";

  revision 2015-06-08 {
    description
      "added esc_serila_ports";
  }

  grouping ncs_template_esc_serial_ports {
    container serial_ports {
      list serial_port {
        // NCS patched for predictable order
        ordered-by user;
        key "serial";
        leaf serial {
          type string;
          description
            "serial port number";
        }
        leaf serial_type {
          type string;
          description
            "serial type, telnet or console";
        }
        // NCS drop must statement
        leaf service_port {
          type string;
          // NCS drop when statement
          description
            "service port number";
        }
        // NCS drop must statement
      }
    }
  }

  grouping ncs_rpc_notif_esc_serial_ports {
    container serial_ports {
      list serial_port {
        key "serial";
        leaf serial {
          type int16 {
            range "0..3";
          }
          description
            "serial port number";
        }
        leaf serial_type {
          type enumeration {
            enum "telnet";
            enum "console";
          }
          description
            "serial type, telnet or console";
        }
        must "serial_type != 'console' or (serial_type = 'console' and serial = '0')" {
          tailf:xpath-root 3;
          error-message "Enter serial_type, console or telnet. Console can only be configured on serial 0. Telnet can be configured on any serial port.";
        }
        leaf service_port {
          type int32 {
            range "7000..8700";
          }
          when '../serial_type = "telnet"' {
            tailf:xpath-root 3;
          }
          description
            "service port number";
        }
        must "serial_type != 'telnet' or (service_port)" {
          tailf:xpath-root 3;
          error-message "Telnet ports need to have service_port number specified";
        }
      }
    }
  }

  grouping live_ncs_esc_serial_ports {
    container serial_ports {
      list serial_port {
        key "serial";
        leaf serial {
          type int16 {
            range "0..3";
          }
          description
            "serial port number";
        }
        leaf serial_type {
          type enumeration {
            enum "telnet";
            enum "console";
          }
          description
            "serial type, telnet or console";
        }
        // NCS drop must statement
        leaf service_port {
          type int32 {
            range "7000..8700";
          }
          // NCS drop when statement
          description
            "service port number";
        }
        // NCS drop must statement
      }
    }
  }

  grouping esc_serial_ports {
    container serial_ports {
      list serial_port {
        key "serial";
        leaf serial {
          type int16 {
            range "0..3";
          }
          description
            "serial port number";
        }
        leaf serial_type {
          type enumeration {
            enum "telnet";
            enum "console";
          }
          description
            "serial type, telnet or console";
        }
        must "serial_type != 'console' or (serial_type = 'console' and serial = '0')" {
          tailf:xpath-root 3;
          error-message "Enter serial_type, console or telnet. Console can only be configured on serial 0. Telnet can be configured on any serial port.";
        }
        leaf service_port {
          type int32 {
            range "7000..8700";
          }
          when '../serial_type = "telnet"' {
            tailf:xpath-root 3;
          }
          description
            "service port number";
        }
        must "serial_type != 'telnet' or (service_port)" {
          tailf:xpath-root 3;
          error-message "Telnet ports need to have service_port number specified";
        }
      }
    }
  }
}
