module esc_opdata_images {
  // Generated by yanger -t ncs
  tailf:mount-id esc-nc-1.0:esc-nc-1.0;
  tailf:ncs-device-type "netconf";

  namespace "http://www.cisco.com/esc/esc_opdata_images";
  prefix esc_opdata_images;

  import ietf-yang-types {
    prefix ietf-yang-types;
  }
  import esc_opdata_image_state_machine {
    prefix opstatemachines;
  }
  import esc_disk {
    prefix disk;
  }
  import "esc-nc-1.0" {
    prefix "esc-nc-1.0";
  }
  import tailf-ncs {
    prefix ncs;
  }
  import tailf-common {
    prefix tailf;
  }

  organization
    "Cisco Systems";
  contact
    "Natasha Shrestha <nashrest@cisco.com>";

  revision 2018-07-24 {
    description
      "Adding image properties to opdata";
  }
  revision 2015-07-06 {
    description
      "Elastic Services Controller Module's images' operational data";
  }

  grouping ncs_template_esc_opdata_images {
    description
      "This contains all the operational data of the images";
    container images {
      list image {
        // NCS patched for predictable order
        ordered-by user;
        description
          "Image running information";
        key "name";
        leaf name {
          description
            "Name of the image";
          type string;
        }
        leaf image_id {
          description
            "ID of the image";
          type string;
        }
        leaf public {
          description
            "True if the image is public";
          type string;
          // NCS drop default statement
        }
        uses opstatemachines:ncs_template_esc_opdata_image_state_machine;
        uses disk:ncs_template_image_properties;
      }
    }
  }

  grouping ncs_rpc_notif_esc_opdata_images {
    description
      "This contains all the operational data of the images";
    container images {
      list image {
        description
          "Image running information";
        key "name";
        leaf name {
          description
            "Name of the image";
          type string;
        }
        leaf image_id {
          description
            "ID of the image";
          type ietf-yang-types:uuid;
        }
        leaf public {
          description
            "True if the image is public";
          type boolean;
          default "true";
        }
        uses opstatemachines:ncs_rpc_notif_esc_opdata_image_state_machine;
        uses disk:ncs_rpc_notif_image_properties;
      }
    }
  }

  grouping live_ncs_esc_opdata_images {
    description
      "This contains all the operational data of the images";
    container images {
      list image {
        description
          "Image running information";
        key "name";
        leaf name {
          description
            "Name of the image";
          type string;
        }
        leaf image_id {
          description
            "ID of the image";
          type ietf-yang-types:uuid;
        }
        leaf public {
          description
            "True if the image is public";
          type boolean;
          // NCS drop default statement
        }
        uses opstatemachines:live_ncs_esc_opdata_image_state_machine;
        uses disk:live_ncs_image_properties;
      }
    }
  }

  grouping esc_opdata_images {
    description
      "This contains all the operational data of the images";
    container images {
      list image {
        description
          "Image running information";
        key "name";
        leaf name {
          description
            "Name of the image";
          type string;
        }
        leaf image_id {
          description
            "ID of the image";
          type ietf-yang-types:uuid;
        }
        leaf public {
          description
            "True if the image is public";
          type boolean;
          default "true";
        }
        uses opstatemachines:esc_opdata_image_state_machine;
        uses disk:image_properties;
      }
    }
  }
}
