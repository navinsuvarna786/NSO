module esc_config_data {
  // Generated by yanger -t ncs
  tailf:mount-id esc-nc-1.0:esc-nc-1.0;
  tailf:ncs-device-type "netconf";

  namespace "http://www.cisco.com/esc/esc_config_data";
  prefix esc_config_data;

  import tailf-common {
    prefix tailf;
  }
  import esc_types {
    prefix types;
  }
  import ietf-inet-types {
    prefix ietf-inet-types;
  }
  import esc_file_locators {
    prefix file_locators;
  }
  import "esc-nc-1.0" {
    prefix "esc-nc-1.0";
  }
  import tailf-ncs {
    prefix ncs;
  }

  organization
    "Cisco Systems";
  contact
    "Shesha Sreenivasamurthy <shesha@cisco.com>";
  description
    "ESC's config data descriptions'";

  revision 2018-11-06 {
    description
      "Change encrypted variable to leaf (NSO cannot support leaf-list).";
  }
  revision 2018-08-29 {
    description
      "Adding config_type and config_options to allow ESC to
       support day0 Params for VNF deployment.";
  }
  revision 2018-08-29 {
    description
      "Added enforce_variable_replacement field.";
  }
  revision 2018-04-02 {
    description
      "Adding config_type and config_options to allow ESC to
       generate ISO files for VNF deployment.";
  }
  revision 2017-11-16 {
    description
      "Deprecate file_locators and add leaf ref (file_locator_name) choice to
       the deployment defined file_locators";
  }
  revision 2017-09-01 {
    description
      "Added file_locators to input_method choice options";
  }
  revision 2016-07-21 {
    description
      "Added template_engine field to configuration to support no token replacement";
  }
  revision 2014-06-23 {
    description
      "ESC Config Data";
  }

  grouping ncs_template_esc_config_data {
    container config_data {
      description
        "This enables to pass day-0 configuration data into the service
         VM. There are two ways: File, and inline data. In either case
         a CDROM is created with the contents of the configuration
         data and is attached to the VM.";
      leaf config_type {
        description
          "Defines how ESC will process the configuration data.
           if empty, it is VIM Specific behaviour.
           The other values supported are CREATE_ISO, CONFIG_DATA_OPTIONS for VIM - CSP";
        type types:ncs_template_config_data_format_type;
      }
      uses ncs_template_config_options {
        description
          "Defines the options requried to process the day 0 file as per config_type.
           For CREATE_ISO config_type, defines the options required to create the file.
           For CONFIG_DATA_OPTIONS config_type, configs data options like additional day-0 configurations";
      }
      list configuration {
        // NCS patched for predictable order
        ordered-by user;
        key "dst";
        description
          "This represents a list of configuration files/templates.
           This being a list allows one to specify multiple day-0
           configurations.";
        choice input_method {
          case file {
            leaf file {
              description
                "ESC downloads the file specified by the URL.
                 This will be used as a template to replace the tokens
                 specified in this template with the values specified in the
                 'variable' section. This field and 'data are mutually
                 exclusive. This template is used to generate the
                 actual day-0 configuration files.";
              type string;
            }
          }
          case data {
            leaf data {
              description
                "Instead of specifying a URL for as template, this allows to
                 use inline text as template. This and 'file', 'encrypted_data',
                 and 'file_locators' elements are mutually exclusive.";
              type types:ncs_template_escbigdata;
            }
          }
          case encrypted_data {
            leaf encrypted_data {
              description
                "Instead of specifying a URL for as template, this allows to
                 use inline text as template. It will be encrypted. This and
                 'file', 'data' and 'file_locators' elements are mutually exclusive.";
              type string;
            }
          }
          case file_locators {
            status deprecated;
            uses file_locators:ncs_template_file_locators_definition {
              description
                "Deprecated. Use file_locator_name.";
            }
          }
          case file_locator_name {
            leaf file_locator_name {
              description
                "Name of a file locator defined in the deployment";
              type string;
            }
          }
        }
        leaf dst {
          description
            "Name of the configuration file that service VM is expecting.";
          type string;
          // NCS drop mandatory statement
        }
        leaf template_engine {
          description
            "Specify the engine you want to use for token replacement";
          type types:ncs_template_template_engine_type;
          // NCS drop default statement
        }
        leaf enforce_variable_replacement {
          description
            "Checks the variables in the day 0 file against the config data section.";
          type string;
          // NCS drop default statement
        }
        list variable {
          // NCS patched for predictable order
          ordered-by user;
          key "name";
          description
            "These are the variables that are specified in the template. This is
             an unbounded list. Each variable should have a name and
             at least one value.  Multiple values can be specified if
             a non zero value is specified to 'min' and 'max' in the
             scaling section. The values here are treated as a pool
             and is managed by ESC.  ESC picks up one value each time
             it spins a new VM either because scaling or because a
             value greater than 1 is specified for 'min' in the
             scaling section. When the VMs are destroyed because of
             scale-in the values are returned back to the pool";
          leaf name {
            description
              "Name of the variable.
               This is case sensitive and should match exactly
               as given in the template. ESC token manager will scan
               the template file and will replace the FIRST occurrence
               of the variable with the next non-used";
            type types:ncs_template_escname;
            // NCS drop mandatory statement
          }
          choice var_value {
            case val {
              leaf-list val {
                // NCS patched for predictable order
                ordered-by user;
                description
                  "Number of values here should match the max value specified in
                   the scaling section so that we have enough values for all the
                   VMs that can be spun.";
                type types:ncs_template_escbigdata;
              }
            }
            case encrypted_val {
              leaf encrypted_val {
                description
                  "Encrypted variable, value will be hidden from db output and logs.";
                type string;
              }
            }
          }
        }
      }
    }
  }

  grouping ncs_template_config_options {
    container config_options {
      container options {
        list option {
          // NCS patched for predictable order
          ordered-by user;
          key "name";
          description
            "The list of options to be used in handling the config. This is an unbounded
             list. Each option must have a unique name.";
          leaf name {
            description
              "Name indicating purpose of the options, such as genisoimage where the
               value list are the required command line parameters";
            type string;
            // NCS drop mandatory statement
          }
          leaf-list value {
            // NCS patched for predictable order
            ordered-by user;
            description
              "List of data required for processing the options. Possibly command line variables.
               Each element is defined separately, in the case of a parameter with a value it should
               be defined together such as -cmdswitch xyz.";
            type string;
          }
        }
      }
    }
  }

  grouping ncs_rpc_notif_esc_config_data {
    container config_data {
      description
        "This enables to pass day-0 configuration data into the service
         VM. There are two ways: File, and inline data. In either case
         a CDROM is created with the contents of the configuration
         data and is attached to the VM.";
      leaf config_type {
        description
          "Defines how ESC will process the configuration data.
           if empty, it is VIM Specific behaviour.
           The other values supported are CREATE_ISO, CONFIG_DATA_OPTIONS for VIM - CSP";
        type types:ncs_rpc_notif_config_data_format_type;
      }
      uses ncs_rpc_notif_config_options {
        description
          "Defines the options requried to process the day 0 file as per config_type.
           For CREATE_ISO config_type, defines the options required to create the file.
           For CONFIG_DATA_OPTIONS config_type, configs data options like additional day-0 configurations";
      }
      list configuration {
        key "dst";
        description
          "This represents a list of configuration files/templates.
           This being a list allows one to specify multiple day-0
           configurations.";
        choice input_method {
          case file {
            leaf file {
              description
                "ESC downloads the file specified by the URL.
                 This will be used as a template to replace the tokens
                 specified in this template with the values specified in the
                 'variable' section. This field and 'data are mutually
                 exclusive. This template is used to generate the
                 actual day-0 configuration files.";
              type ietf-inet-types:uri;
            }
          }
          case data {
            leaf data {
              description
                "Instead of specifying a URL for as template, this allows to
                 use inline text as template. This and 'file', 'encrypted_data',
                 and 'file_locators' elements are mutually exclusive.";
              type types:ncs_rpc_notif_escbigdata;
            }
          }
          case encrypted_data {
            leaf encrypted_data {
              description
                "Instead of specifying a URL for as template, this allows to
                 use inline text as template. It will be encrypted. This and
                 'file', 'data' and 'file_locators' elements are mutually exclusive.";
              type tailf:aes-cfb-128-encrypted-string;
            }
          }
          case file_locators {
            status deprecated;
            uses file_locators:ncs_rpc_notif_file_locators_definition {
              description
                "Deprecated. Use file_locator_name.";
            }
          }
          case file_locator_name {
            leaf file_locator_name {
              description
                "Name of a file locator defined in the deployment";
              type leafref {
                path "../../../../file_locators/file_locator/name";
              }
            }
          }
        }
        leaf dst {
          description
            "Name of the configuration file that service VM is expecting.";
          type string {
            length "1..1024";
          }
          mandatory true;
        }
        leaf template_engine {
          description
            "Specify the engine you want to use for token replacement";
          type types:ncs_rpc_notif_template_engine_type;
          default "VELOCITY";
        }
        leaf enforce_variable_replacement {
          description
            "Checks the variables in the day 0 file against the config data section.";
          type boolean;
          default "false";
        }
        list variable {
          key "name";
          description
            "These are the variables that are specified in the template. This is
             an unbounded list. Each variable should have a name and
             at least one value.  Multiple values can be specified if
             a non zero value is specified to 'min' and 'max' in the
             scaling section. The values here are treated as a pool
             and is managed by ESC.  ESC picks up one value each time
             it spins a new VM either because scaling or because a
             value greater than 1 is specified for 'min' in the
             scaling section. When the VMs are destroyed because of
             scale-in the values are returned back to the pool";
          leaf name {
            description
              "Name of the variable.
               This is case sensitive and should match exactly
               as given in the template. ESC token manager will scan
               the template file and will replace the FIRST occurrence
               of the variable with the next non-used";
            type types:ncs_rpc_notif_escname;
            mandatory true;
          }
          choice var_value {
            case val {
              leaf-list val {
                description
                  "Number of values here should match the max value specified in
                   the scaling section so that we have enough values for all the
                   VMs that can be spun.";
                type types:ncs_rpc_notif_escbigdata;
              }
            }
            case encrypted_val {
              leaf encrypted_val {
                description
                  "Encrypted variable, value will be hidden from db output and logs.";
                type tailf:aes-cfb-128-encrypted-string;
              }
            }
          }
        }
      }
    }
  }

  grouping ncs_rpc_notif_config_options {
    container config_options {
      container options {
        list option {
          key "name";
          description
            "The list of options to be used in handling the config. This is an unbounded
             list. Each option must have a unique name.";
          leaf name {
            description
              "Name indicating purpose of the options, such as genisoimage where the
               value list are the required command line parameters";
            type string;
            mandatory true;
          }
          leaf-list value {
            description
              "List of data required for processing the options. Possibly command line variables.
               Each element is defined separately, in the case of a parameter with a value it should
               be defined together such as -cmdswitch xyz.";
            type string;
          }
        }
      }
    }
  }

  grouping live_ncs_esc_config_data {
    container config_data {
      description
        "This enables to pass day-0 configuration data into the service
         VM. There are two ways: File, and inline data. In either case
         a CDROM is created with the contents of the configuration
         data and is attached to the VM.";
      leaf config_type {
        description
          "Defines how ESC will process the configuration data.
           if empty, it is VIM Specific behaviour.
           The other values supported are CREATE_ISO, CONFIG_DATA_OPTIONS for VIM - CSP";
        type types:live_ncs_config_data_format_type;
      }
      uses live_ncs_config_options {
        description
          "Defines the options requried to process the day 0 file as per config_type.
           For CREATE_ISO config_type, defines the options required to create the file.
           For CONFIG_DATA_OPTIONS config_type, configs data options like additional day-0 configurations";
      }
      list configuration {
        key "dst";
        description
          "This represents a list of configuration files/templates.
           This being a list allows one to specify multiple day-0
           configurations.";
        choice input_method {
          case file {
            leaf file {
              description
                "ESC downloads the file specified by the URL.
                 This will be used as a template to replace the tokens
                 specified in this template with the values specified in the
                 'variable' section. This field and 'data are mutually
                 exclusive. This template is used to generate the
                 actual day-0 configuration files.";
              type ietf-inet-types:uri;
            }
          }
          case data {
            leaf data {
              description
                "Instead of specifying a URL for as template, this allows to
                 use inline text as template. This and 'file', 'encrypted_data',
                 and 'file_locators' elements are mutually exclusive.";
              type types:live_ncs_escbigdata;
            }
          }
          case encrypted_data {
            leaf encrypted_data {
              description
                "Instead of specifying a URL for as template, this allows to
                 use inline text as template. It will be encrypted. This and
                 'file', 'data' and 'file_locators' elements are mutually exclusive.";
              type tailf:aes-cfb-128-encrypted-string;
            }
          }
          case file_locators {
            status deprecated;
            uses file_locators:live_ncs_file_locators_definition {
              description
                "Deprecated. Use file_locator_name.";
            }
          }
          case file_locator_name {
            leaf file_locator_name {
              description
                "Name of a file locator defined in the deployment";
              type leafref {
                path "../../../../file_locators/file_locator/name";
              }
            }
          }
        }
        leaf dst {
          description
            "Name of the configuration file that service VM is expecting.";
          type string {
            length "1..1024";
          }
          // NCS drop mandatory statement
        }
        leaf template_engine {
          description
            "Specify the engine you want to use for token replacement";
          type types:live_ncs_template_engine_type;
          // NCS drop default statement
        }
        leaf enforce_variable_replacement {
          description
            "Checks the variables in the day 0 file against the config data section.";
          type boolean;
          // NCS drop default statement
        }
        list variable {
          key "name";
          description
            "These are the variables that are specified in the template. This is
             an unbounded list. Each variable should have a name and
             at least one value.  Multiple values can be specified if
             a non zero value is specified to 'min' and 'max' in the
             scaling section. The values here are treated as a pool
             and is managed by ESC.  ESC picks up one value each time
             it spins a new VM either because scaling or because a
             value greater than 1 is specified for 'min' in the
             scaling section. When the VMs are destroyed because of
             scale-in the values are returned back to the pool";
          leaf name {
            description
              "Name of the variable.
               This is case sensitive and should match exactly
               as given in the template. ESC token manager will scan
               the template file and will replace the FIRST occurrence
               of the variable with the next non-used";
            type types:live_ncs_escname;
            // NCS drop mandatory statement
          }
          choice var_value {
            case val {
              leaf-list val {
                description
                  "Number of values here should match the max value specified in
                   the scaling section so that we have enough values for all the
                   VMs that can be spun.";
                type types:live_ncs_escbigdata;
              }
            }
            case encrypted_val {
              leaf encrypted_val {
                description
                  "Encrypted variable, value will be hidden from db output and logs.";
                type tailf:aes-cfb-128-encrypted-string;
              }
            }
          }
        }
      }
    }
  }

  grouping live_ncs_config_options {
    container config_options {
      container options {
        list option {
          key "name";
          description
            "The list of options to be used in handling the config. This is an unbounded
             list. Each option must have a unique name.";
          leaf name {
            description
              "Name indicating purpose of the options, such as genisoimage where the
               value list are the required command line parameters";
            type string;
            // NCS drop mandatory statement
          }
          leaf-list value {
            description
              "List of data required for processing the options. Possibly command line variables.
               Each element is defined separately, in the case of a parameter with a value it should
               be defined together such as -cmdswitch xyz.";
            type string;
          }
        }
      }
    }
  }

  grouping esc_config_data {
    container config_data {
      description
        "This enables to pass day-0 configuration data into the service
         VM. There are two ways: File, and inline data. In either case
         a CDROM is created with the contents of the configuration
         data and is attached to the VM.";
      leaf config_type {
        description
          "Defines how ESC will process the configuration data.
           if empty, it is VIM Specific behaviour.
           The other values supported are CREATE_ISO, CONFIG_DATA_OPTIONS for VIM - CSP";
        type types:config_data_format_type;
      }
      uses config_options {
        description
          "Defines the options requried to process the day 0 file as per config_type.
           For CREATE_ISO config_type, defines the options required to create the file.
           For CONFIG_DATA_OPTIONS config_type, configs data options like additional day-0 configurations";
      }
      list configuration {
        key "dst";
        description
          "This represents a list of configuration files/templates.
           This being a list allows one to specify multiple day-0
           configurations.";
        choice input_method {
          case file {
            leaf file {
              description
                "ESC downloads the file specified by the URL.
                 This will be used as a template to replace the tokens
                 specified in this template with the values specified in the
                 'variable' section. This field and 'data are mutually
                 exclusive. This template is used to generate the
                 actual day-0 configuration files.";
              type ietf-inet-types:uri;
            }
          }
          case data {
            leaf data {
              description
                "Instead of specifying a URL for as template, this allows to
                 use inline text as template. This and 'file', 'encrypted_data',
                 and 'file_locators' elements are mutually exclusive.";
              type types:escbigdata;
            }
          }
          case encrypted_data {
            leaf encrypted_data {
              tailf:ned-ignore-compare-config;
              description
                "Instead of specifying a URL for as template, this allows to
                 use inline text as template. It will be encrypted. This and
                 'file', 'data' and 'file_locators' elements are mutually exclusive.";
              type tailf:aes-cfb-128-encrypted-string;
            }
          }
          case file_locators {
            status deprecated;
            uses file_locators:file_locators_definition {
              description
                "Deprecated. Use file_locator_name.";
            }
          }
          case file_locator_name {
            leaf file_locator_name {
              description
                "Name of a file locator defined in the deployment";
              type leafref {
                path "../../../../file_locators/file_locator/name";
              }
            }
          }
        }
        leaf dst {
          description
            "Name of the configuration file that service VM is expecting.";
          type string {
            length "1..1024";
          }
          mandatory true;
        }
        leaf template_engine {
          description
            "Specify the engine you want to use for token replacement";
          type types:template_engine_type;
          default "VELOCITY";
        }
        leaf enforce_variable_replacement {
          description
            "Checks the variables in the day 0 file against the config data section.";
          type boolean;
          default "false";
        }
        list variable {
          key "name";
          description
            "These are the variables that are specified in the template. This is
             an unbounded list. Each variable should have a name and
             at least one value.  Multiple values can be specified if
             a non zero value is specified to 'min' and 'max' in the
             scaling section. The values here are treated as a pool
             and is managed by ESC.  ESC picks up one value each time
             it spins a new VM either because scaling or because a
             value greater than 1 is specified for 'min' in the
             scaling section. When the VMs are destroyed because of
             scale-in the values are returned back to the pool";
          leaf name {
            description
              "Name of the variable.
               This is case sensitive and should match exactly
               as given in the template. ESC token manager will scan
               the template file and will replace the FIRST occurrence
               of the variable with the next non-used";
            type types:escname;
            mandatory true;
          }
          choice var_value {
            case val {
              leaf-list val {
                description
                  "Number of values here should match the max value specified in
                   the scaling section so that we have enough values for all the
                   VMs that can be spun.";
                type types:escbigdata;
              }
            }
            case encrypted_val {
              leaf encrypted_val {
                tailf:ned-ignore-compare-config;
                description
                  "Encrypted variable, value will be hidden from db output and logs.";
                type tailf:aes-cfb-128-encrypted-string;
              }
            }
          }
        }
      }
    }
  }

  grouping config_options {
    container config_options {
      container options {
        list option {
          key "name";
          description
            "The list of options to be used in handling the config. This is an unbounded
             list. Each option must have a unique name.";
          leaf name {
            description
              "Name indicating purpose of the options, such as genisoimage where the
               value list are the required command line parameters";
            type string;
            mandatory true;
          }
          leaf-list value {
            description
              "List of data required for processing the options. Possibly command line variables.
               Each element is defined separately, in the case of a parameter with a value it should
               be defined together such as -cmdswitch xyz.";
            type string;
          }
        }
      }
    }
  }
}
