module esc_datamodel {
  // Generated by yanger -t ncs
  tailf:mount-id esc-nc-1.0:esc-nc-1.0;
  tailf:ncs-device-type "netconf";

  namespace "http://www.cisco.com/esc/esc_datamodel";
  prefix esc_datamodel;

  import esc_policies {
    prefix policies;
  }
  import esc_network {
    prefix network;
  }
  import esc_volume {
    prefix volume;
  }
  import esc_interface {
    prefix interface;
  }
  import esc_kpi {
    prefix kpi;
  }
  import esc_rules {
    prefix rules;
  }
  import esc_config_data {
    prefix cfg;
  }
  import esc_port_forwarding {
    prefix pf;
  }
  import esc_scaling {
    prefix scaling;
  }
  import esc_types {
    prefix types;
  }
  import esc_extension {
    prefix extension;
  }
  import esc_locators {
    prefix locators;
  }
  import esc_file_locators {
    prefix file_locators;
  }
  import tailf-common {
    prefix tailf;
  }
  include esc_serial_ports;
  import esc_container_services {
    prefix esc_container_services;
  }
  import "esc-nc-1.0" {
    prefix "esc-nc-1.0";
  }
  import tailf-ncs {
    prefix ncs;
  }

  organization
    "Cisco Systems";
  contact
    "Shesha Sreenivasamurthy <shesha@cisco.com>";

  revision 2020-01-28 {
    description
      "Removed mandatory attribute for  bootup_time";
  }
  revision 2018-05-25 {
    description
      "Added extension list to deployment.";
  }
  revision 2017-11-07 {
    description
      "Added file_locators to deployment.";
  }
  revision 2017-10-07 {
    description
      "Added esc_serial_ports to allow serial port creation at deployment time.";
  }
  revision 2017-05-18 {
    description
      "Added vim_vm_name vm_group to allow custom vm names for deployment.";
  }
  revision 2017-05-08 {
    description
      "Updated recovery_wait_time to be non mandatory with a default value of 0.";
  }
  revision 2017-03-10 {
    description
      "Added locator under vm_group to identify the target vim for deployment.";
  }
  revision 2017-01-13 {
    description
      "Removed services and service definition";
  }
  revision 2016-10-04 {
    description
      "Added reboot_time";
  }
  revision 2016-04-13 {
    description
      "Added a generic policy container under vm_group";
  }
  revision 2016-03-16 {
    description
      "Added use of locators";
  }
  revision 2015-11-09 {
    description
      "Added a leaf to support volume that was precreated in VIM";
  }
  revision 2015-09-21 {
    description
      "Added a leaf to config if redeploy is needed after reboot fails upon recovery";
  }
  revision 2015-07-14 {
    description
      "Added a new deployment model under tenant";
  }
  revision 2015-06-17 {
    description
      "ESC Datamodel change to add image and flavor that was precreated in vim";
  }
  revision 2015-06-08 {
    description
      "added esc_port_forwarding";
  }
  revision 2015-06-04 {
    description
      "updated description";
  }
  revision 2014-06-23 {
    description
      "ESC Datamodel";
  }

  grouping ncs_template_misc_params {
    container misc {
      description
        "Some miscellaneous configurations.";
      container watchdog {
        description
          "Watch Dog";
        leaf hardware {
          description
            "Watchdog device to be used. i6300esb or ib700";
          type types:ncs_template_wd_hardware;
        }
        leaf action {
          description
            "Action when watchdog fires:
             reset|shutdown|poweroff|pause|debug|none";
          type types:ncs_template_wd_action;
        }
      }
    }
  }

  grouping ncs_template_datamodel {
    uses policies:ncs_template_esc_policies;
    uses network:ncs_template_esc_network;
    uses file_locators:ncs_template_file_locators_definition {
      description
        "List of files required by the deployment that are local
         or remote with supporting data for retrieval and retention";
    }
    list vm_group {
      // NCS patched for predictable order
      ordered-by user;
      description
        "This section allows one to define properties such as number of interfaces, type of
         monitoring, monitoring frequency, type of eventing, scaling
         mechanism, elasticity properties, etc for each VM in this
         group. This represents a type of VM.  For example, if one
         needs two Webservers in a deployment, only one VM instance is
         defined and number of instances is set to 2 in the scaling
         section. If there are two types of VMs, for example a
         Webserver and a Database server, then such a service will
         have two vm_groups: one for Webserver and another for
         Database server";
      key "name";
      // NCS drop min-elements statement
      leaf name {
        description
          "A name for the VM group";
        type types:ncs_template_escname;
        // NCS drop mandatory statement
      }
      uses locators:ncs_template_locators;
      leaf image {
        description
          "Image refers to pre-existing image in VIM";
        type types:ncs_template_escname;
      }
      leaf flavor {
        description
          "Flavor refers to pre-existing flavor in VIM";
        type types:ncs_template_escname;
      }
      leaf vim_vm_name {
        description
          "User specified name for the VM on the VIM";
        type types:ncs_template_escname;
      }
      leaf volume {
        description
          "Volume refers to pre-existing volume in VIM";
        type types:ncs_template_escname;
      }
      leaf software_version {
        description
          "Software version of the VM group";
        type types:ncs_template_escname;
      }
      leaf bootup_time {
        description
          "Time in seconds that this VM takes to perform a cold boot. This will
           be the time that ESC waits before deciding that the VM is
           un-bootable.";
        type string;
      }
      leaf recovery_wait_time {
        description
          "Time in seconds that this VM takes to perform a normal warm
           reboot. This will be used to avoid premature VM recovery in
           case VM becomes unresponsive due to operator reboot. This
           is important as VM recovery will results in loss of data
           that is stored on root disk. If speedy recovery is more
           important than the data on the root disk, this value can be
           optionally set to 0.";
        type string;
        // NCS drop default statement
      }
      leaf reboot_time {
        description
          "Time in seconds that this VM takes to perform a normal reboot.
           if not specified, it will use bootup_time value.";
        type string;
      }
      container policies {
        uses policies:ncs_template_esc_policy;
      }
      uses ncs_template_misc_params;
      uses volume:ncs_template_esc_volume_deployment;
      uses interface:ncs_template_esc_interface;
      uses kpi:ncs_template_esc_kpi;
      uses rules:ncs_template_esc_rules;
      uses rules:ncs_template_lcm_rules;
      uses cfg:ncs_template_esc_config_data;
      uses pf:ncs_template_esc_port_forwarding;
      uses scaling:ncs_template_esc_scaling;
      uses policies:ncs_template_intra_vm_group_placement;
      uses policies:ncs_template_intra_vm_group_properties;
      uses policies:ncs_template_recovery_policies;
      uses policies:ncs_template_vmexport_policies;
      uses extension:ncs_template_extension_list_definition;
      uses ncs_template_esc_serial_ports;
      uses ncs_template_esc_vnc;
    }
  }

  grouping ncs_template_tenant_dep_model {
    container deployments {
      list deployment {
        // NCS patched for predictable order
        ordered-by user;
        key "name";
        description
          "List of deployments requested by the user";
        leaf name {
          description
            "User specified name. One can have multiple deployments with a unique name for each
             deployment";
          type types:ncs_template_escname;
          // NCS drop mandatory statement
        }
        uses locators:ncs_template_extensible_locators;
        uses ncs_template_datamodel;
        uses esc_container_services:ncs_template_services;
        uses rules:ncs_template_lcm_rules;
        uses extension:ncs_template_extension_list_definition;
        container deployment_groups {
          leaf-list anti_affinity_group {
            // NCS patched for predictable order
            ordered-by user;
            description
              "Reference to the anti-affinity groups to which this deployment pertains to.
               That is, any deployment referencing the same anti-affinity group (in the present or future)
               will have an anti-affinity relationship to this deployment.";
            type string;
          }
        }
      }
    }
  }

  grouping ncs_template_esc_vnc {
    container vnc {
      description
        "VNC of the vm group";
      leaf password {
        description
          "VNC password attribute in clear text";
        type string;
      }
    }
  }

  grouping ncs_rpc_notif_misc_params {
    container misc {
      description
        "Some miscellaneous configurations.";
      container watchdog {
        description
          "Watch Dog";
        leaf hardware {
          description
            "Watchdog device to be used. i6300esb or ib700";
          type types:ncs_rpc_notif_wd_hardware;
        }
        leaf action {
          description
            "Action when watchdog fires:
             reset|shutdown|poweroff|pause|debug|none";
          type types:ncs_rpc_notif_wd_action;
        }
      }
    }
  }

  grouping ncs_rpc_notif_datamodel {
    uses policies:ncs_rpc_notif_esc_policies;
    uses network:ncs_rpc_notif_esc_network;
    uses file_locators:ncs_rpc_notif_file_locators_definition {
      description
        "List of files required by the deployment that are local
         or remote with supporting data for retrieval and retention";
    }
    list vm_group {
      description
        "This section allows one to define properties such as number of interfaces, type of
         monitoring, monitoring frequency, type of eventing, scaling
         mechanism, elasticity properties, etc for each VM in this
         group. This represents a type of VM.  For example, if one
         needs two Webservers in a deployment, only one VM instance is
         defined and number of instances is set to 2 in the scaling
         section. If there are two types of VMs, for example a
         Webserver and a Database server, then such a service will
         have two vm_groups: one for Webserver and another for
         Database server";
      key "name";
      min-elements 1;
      leaf name {
        description
          "A name for the VM group";
        type types:ncs_rpc_notif_escname;
        mandatory true;
      }
      uses locators:ncs_rpc_notif_locators;
      leaf image {
        description
          "Image refers to pre-existing image in VIM";
        type types:ncs_rpc_notif_escname;
      }
      leaf flavor {
        description
          "Flavor refers to pre-existing flavor in VIM";
        type types:ncs_rpc_notif_escname;
      }
      leaf vim_vm_name {
        description
          "User specified name for the VM on the VIM";
        type types:ncs_rpc_notif_escname;
      }
      leaf volume {
        description
          "Volume refers to pre-existing volume in VIM";
        type types:ncs_rpc_notif_escname;
      }
      leaf software_version {
        description
          "Software version of the VM group";
        type types:ncs_rpc_notif_escname;
      }
      leaf bootup_time {
        description
          "Time in seconds that this VM takes to perform a cold boot. This will
           be the time that ESC waits before deciding that the VM is
           un-bootable.";
        type int32;
      }
      leaf recovery_wait_time {
        description
          "Time in seconds that this VM takes to perform a normal warm
           reboot. This will be used to avoid premature VM recovery in
           case VM becomes unresponsive due to operator reboot. This
           is important as VM recovery will results in loss of data
           that is stored on root disk. If speedy recovery is more
           important than the data on the root disk, this value can be
           optionally set to 0.";
        type int32;
        default "900";
      }
      leaf reboot_time {
        description
          "Time in seconds that this VM takes to perform a normal reboot.
           if not specified, it will use bootup_time value.";
        type int32;
      }
      container policies {
        uses policies:ncs_rpc_notif_esc_policy;
      }
      uses ncs_rpc_notif_misc_params;
      uses volume:ncs_rpc_notif_esc_volume_deployment;
      uses interface:ncs_rpc_notif_esc_interface;
      uses kpi:ncs_rpc_notif_esc_kpi;
      uses rules:ncs_rpc_notif_esc_rules;
      uses rules:ncs_rpc_notif_lcm_rules;
      uses cfg:ncs_rpc_notif_esc_config_data;
      uses pf:ncs_rpc_notif_esc_port_forwarding;
      uses scaling:ncs_rpc_notif_esc_scaling;
      uses policies:ncs_rpc_notif_intra_vm_group_placement;
      uses policies:ncs_rpc_notif_intra_vm_group_properties;
      uses policies:ncs_rpc_notif_recovery_policies;
      uses policies:ncs_rpc_notif_vmexport_policies;
      uses extension:ncs_rpc_notif_extension_list_definition;
      uses ncs_rpc_notif_esc_serial_ports;
      uses ncs_rpc_notif_esc_vnc;
    }
  }

  grouping ncs_rpc_notif_tenant_dep_model {
    container deployments {
      list deployment {
        key "name";
        description
          "List of deployments requested by the user";
        leaf name {
          description
            "User specified name. One can have multiple deployments with a unique name for each
             deployment";
          type types:ncs_rpc_notif_escname;
          mandatory true;
        }
        uses locators:ncs_rpc_notif_extensible_locators;
        uses ncs_rpc_notif_datamodel;
        uses esc_container_services:ncs_rpc_notif_services;
        uses rules:ncs_rpc_notif_lcm_rules;
        uses extension:ncs_rpc_notif_extension_list_definition;
        container deployment_groups {
          leaf-list anti_affinity_group {
            description
              "Reference to the anti-affinity groups to which this deployment pertains to.
               That is, any deployment referencing the same anti-affinity group (in the present or future)
               will have an anti-affinity relationship to this deployment.";
            type string;
          }
        }
      }
    }
  }

  grouping ncs_rpc_notif_esc_vnc {
    container vnc {
      description
        "VNC of the vm group";
      leaf password {
        description
          "VNC password attribute in clear text";
        type tailf:aes-cfb-128-encrypted-string;
      }
    }
  }

  grouping live_ncs_misc_params {
    container misc {
      description
        "Some miscellaneous configurations.";
      container watchdog {
        description
          "Watch Dog";
        leaf hardware {
          description
            "Watchdog device to be used. i6300esb or ib700";
          type types:live_ncs_wd_hardware;
        }
        leaf action {
          description
            "Action when watchdog fires:
             reset|shutdown|poweroff|pause|debug|none";
          type types:live_ncs_wd_action;
        }
      }
    }
  }

  grouping live_ncs_datamodel {
    uses policies:live_ncs_esc_policies;
    uses network:live_ncs_esc_network;
    uses file_locators:live_ncs_file_locators_definition {
      description
        "List of files required by the deployment that are local
         or remote with supporting data for retrieval and retention";
    }
    list vm_group {
      description
        "This section allows one to define properties such as number of interfaces, type of
         monitoring, monitoring frequency, type of eventing, scaling
         mechanism, elasticity properties, etc for each VM in this
         group. This represents a type of VM.  For example, if one
         needs two Webservers in a deployment, only one VM instance is
         defined and number of instances is set to 2 in the scaling
         section. If there are two types of VMs, for example a
         Webserver and a Database server, then such a service will
         have two vm_groups: one for Webserver and another for
         Database server";
      key "name";
      // NCS drop min-elements statement
      leaf name {
        description
          "A name for the VM group";
        type types:live_ncs_escname;
        // NCS drop mandatory statement
      }
      uses locators:live_ncs_locators;
      leaf image {
        description
          "Image refers to pre-existing image in VIM";
        type types:live_ncs_escname;
      }
      leaf flavor {
        description
          "Flavor refers to pre-existing flavor in VIM";
        type types:live_ncs_escname;
      }
      leaf vim_vm_name {
        description
          "User specified name for the VM on the VIM";
        type types:live_ncs_escname;
      }
      leaf volume {
        description
          "Volume refers to pre-existing volume in VIM";
        type types:live_ncs_escname;
      }
      leaf software_version {
        description
          "Software version of the VM group";
        type types:live_ncs_escname;
      }
      leaf bootup_time {
        description
          "Time in seconds that this VM takes to perform a cold boot. This will
           be the time that ESC waits before deciding that the VM is
           un-bootable.";
        type int32;
      }
      leaf recovery_wait_time {
        description
          "Time in seconds that this VM takes to perform a normal warm
           reboot. This will be used to avoid premature VM recovery in
           case VM becomes unresponsive due to operator reboot. This
           is important as VM recovery will results in loss of data
           that is stored on root disk. If speedy recovery is more
           important than the data on the root disk, this value can be
           optionally set to 0.";
        type int32;
        // NCS drop default statement
      }
      leaf reboot_time {
        description
          "Time in seconds that this VM takes to perform a normal reboot.
           if not specified, it will use bootup_time value.";
        type int32;
      }
      container policies {
        uses policies:live_ncs_esc_policy;
      }
      uses live_ncs_misc_params;
      uses volume:live_ncs_esc_volume_deployment;
      uses interface:live_ncs_esc_interface;
      uses kpi:live_ncs_esc_kpi;
      uses rules:live_ncs_esc_rules;
      uses rules:live_ncs_lcm_rules;
      uses cfg:live_ncs_esc_config_data;
      uses pf:live_ncs_esc_port_forwarding;
      uses scaling:live_ncs_esc_scaling;
      uses policies:live_ncs_intra_vm_group_placement;
      uses policies:live_ncs_intra_vm_group_properties;
      uses policies:live_ncs_recovery_policies;
      uses policies:live_ncs_vmexport_policies;
      uses extension:live_ncs_extension_list_definition;
      uses live_ncs_esc_serial_ports;
      uses live_ncs_esc_vnc;
    }
  }

  grouping live_ncs_tenant_dep_model {
    container deployments {
      list deployment {
        key "name";
        description
          "List of deployments requested by the user";
        leaf name {
          description
            "User specified name. One can have multiple deployments with a unique name for each
             deployment";
          type types:live_ncs_escname;
          // NCS drop mandatory statement
        }
        uses locators:live_ncs_extensible_locators;
        uses live_ncs_datamodel;
        uses esc_container_services:live_ncs_services;
        uses rules:live_ncs_lcm_rules;
        uses extension:live_ncs_extension_list_definition;
        container deployment_groups {
          leaf-list anti_affinity_group {
            description
              "Reference to the anti-affinity groups to which this deployment pertains to.
               That is, any deployment referencing the same anti-affinity group (in the present or future)
               will have an anti-affinity relationship to this deployment.";
            type string;
          }
        }
      }
    }
  }

  grouping live_ncs_esc_vnc {
    container vnc {
      description
        "VNC of the vm group";
      leaf password {
        description
          "VNC password attribute in clear text";
        type tailf:aes-cfb-128-encrypted-string;
      }
    }
  }

  grouping misc_params {
    container misc {
      description
        "Some miscellaneous configurations.";
      container watchdog {
        description
          "Watch Dog";
        leaf hardware {
          description
            "Watchdog device to be used. i6300esb or ib700";
          type types:wd_hardware;
        }
        leaf action {
          description
            "Action when watchdog fires:
             reset|shutdown|poweroff|pause|debug|none";
          type types:wd_action;
        }
      }
    }
  }

  grouping datamodel {
    uses policies:esc_policies;
    uses network:esc_network;
    uses file_locators:file_locators_definition {
      description
        "List of files required by the deployment that are local
         or remote with supporting data for retrieval and retention";
    }
    list vm_group {
      description
        "This section allows one to define properties such as number of interfaces, type of
         monitoring, monitoring frequency, type of eventing, scaling
         mechanism, elasticity properties, etc for each VM in this
         group. This represents a type of VM.  For example, if one
         needs two Webservers in a deployment, only one VM instance is
         defined and number of instances is set to 2 in the scaling
         section. If there are two types of VMs, for example a
         Webserver and a Database server, then such a service will
         have two vm_groups: one for Webserver and another for
         Database server";
      key "name";
      min-elements 1;
      leaf name {
        description
          "A name for the VM group";
        type types:escname;
        mandatory true;
      }
      uses locators:locators;
      leaf image {
        description
          "Image refers to pre-existing image in VIM";
        type types:escname;
      }
      leaf flavor {
        description
          "Flavor refers to pre-existing flavor in VIM";
        type types:escname;
      }
      leaf vim_vm_name {
        description
          "User specified name for the VM on the VIM";
        type types:escname;
      }
      leaf volume {
        description
          "Volume refers to pre-existing volume in VIM";
        type types:escname;
      }
      leaf software_version {
        description
          "Software version of the VM group";
        type types:escname;
      }
      leaf bootup_time {
        description
          "Time in seconds that this VM takes to perform a cold boot. This will
           be the time that ESC waits before deciding that the VM is
           un-bootable.";
        type int32;
      }
      leaf recovery_wait_time {
        description
          "Time in seconds that this VM takes to perform a normal warm
           reboot. This will be used to avoid premature VM recovery in
           case VM becomes unresponsive due to operator reboot. This
           is important as VM recovery will results in loss of data
           that is stored on root disk. If speedy recovery is more
           important than the data on the root disk, this value can be
           optionally set to 0.";
        type int32;
        default "900";
      }
      leaf reboot_time {
        description
          "Time in seconds that this VM takes to perform a normal reboot.
           if not specified, it will use bootup_time value.";
        type int32;
      }
      container policies {
        uses policies:esc_policy;
      }
      uses misc_params;
      uses volume:esc_volume_deployment;
      uses interface:esc_interface;
      uses kpi:esc_kpi;
      uses rules:esc_rules;
      uses rules:lcm_rules;
      uses cfg:esc_config_data;
      uses pf:esc_port_forwarding;
      uses scaling:esc_scaling;
      uses policies:intra_vm_group_placement;
      uses policies:intra_vm_group_properties;
      uses policies:recovery_policies;
      uses policies:vmexport_policies;
      uses extension:extension_list_definition;
      uses esc_serial_ports;
      uses esc_vnc;
    }
  }

  grouping tenant_dep_model {
    container deployments {
      list deployment {
        key "name";
        description
          "List of deployments requested by the user";
        leaf name {
          description
            "User specified name. One can have multiple deployments with a unique name for each
             deployment";
          type types:escname;
          mandatory true;
        }
        uses locators:extensible_locators;
        uses datamodel;
        uses esc_container_services:services;
        uses rules:lcm_rules;
        uses extension:extension_list_definition;
        container deployment_groups {
          leaf-list anti_affinity_group {
            description
              "Reference to the anti-affinity groups to which this deployment pertains to.
               That is, any deployment referencing the same anti-affinity group (in the present or future)
               will have an anti-affinity relationship to this deployment.";
            type string;
          }
        }
      }
    }
  }

  grouping esc_vnc {
    container vnc {
      description
        "VNC of the vm group";
      leaf password {
        tailf:ned-ignore-compare-config;
        description
          "VNC password attribute in clear text";
        type tailf:aes-cfb-128-encrypted-string;
      }
    }
  }
}
