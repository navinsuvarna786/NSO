module esc_opdata_flavor_state_machine {

  /*
   * This represents operational data of the flavor state machine
   */

  namespace "http://www.cisco.com/esc/esc_opdata_flavor_state_machines";
  prefix "esc_opdata_flavor_state_machine";

  import esc_types { prefix "types"; }

  organization "Cisco Systems";

  contact "Elie El Ajaltouni <eelajalt@cisco.com>";

  revision 2015-11-24 {
    description
      "Elastic Services Controller Module's flavor state machines operational data";
  }

  grouping esc_opdata_flavor_state_machine {
    description
      "This contains all the operational data of the flavor
       state machine";
    leaf flavor_name {
      description "Name uniquely identifies a Flavor";
      type string;
    }

    leaf state {
      description "State in which Flavor is currently in";
      type types:flavor_state_machine_states;
    }
  }
}
