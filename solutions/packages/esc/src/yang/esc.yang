module esc {
  /*
   * This is the top level YANG module. This imports the datamodel
   * module and that import the rest of YANG modules.
   */
  namespace "http://www.cisco.com/esc/esc";
  prefix "esc";

  import esc_datamodel { prefix "dm"; }
  import tailf-common { prefix "tailf"; }
  import esc_opdata { prefix "op"; }
  import esc_info {prefix "info"; }
  import esc_types { prefix "types"; }
  import esc_network { prefix "network"; }
  import esc_disk { prefix "disk"; }
  import esc_flavor { prefix "flavor"; }
  import esc_vim_connector { prefix "vim"; }
  import esc_volume { prefix "volume"; }
  import esc_property { prefix "property"; }
  import esc_file_server { prefix "file_servers"; }
  import esc_extension { prefix "extension"; }
  import esc_config_parameter { prefix "configparams"; }

  include "esc_notifications";

  organization "Cisco Systems";

  contact "Shesha Sreenivasamurthy <shesha@cisco.com>";

  description
    "YANG version of the Elastic Service Controller.  This is a complete
     service orchestration module that can dynamically expand and
     reduce your service capacity based on your description of
     LOAD. This module guarantees that the services will be online
     until you tear it down.  This module enables your to: (config it)
     -> (deploy it) -> (forget it)";
 revision 2020-06-09 {
    description "Added optional vmExportAction parameter includeImage";
  }
  revision 2020-04-27 {
    description "Added new rpc calculateVMLCExportSize";
  }
  revision 2020-03-27 {
    description "Added 2 new actions VmImageFlavorExport and VmImageFlavorImport";
    }
  revision 2019-10-04 {
    description "Added importDeploymentData RPC";
  }
  revision 2018-11-14 {
    description "removed optional vm export actionType and changed name to vmExportAction";
  }
  revision 2018-10-31 {
    description "added optional vm export backup path to vmBackupAction and added properties to support configurable VNF manual recovery";
  }
  revision 2018-10-02 {
    description "added vm import action rpc input definition";
  }
  revision 2018-09-19 {
    description "Added properties to support configurable VM manual recovery";
  }
  revision 2018-08-29 {
    description "Added extension for tenant to support quota settings";
  }
  revision 2018-08-08 {
    description "added service restoration rpc input definition";
  }
  revision 2018-02-20 {
    description "Added VIM connector status checking action";
  }
  revision 2018-01-23 {
    description "Added checkVmBeforeRecovery option for recovery vm action";
  }
  revision 2017-10-07 {
    description "Added serial port support";
  }
  revision 2017-09-25 {
    description "Added file server config usage";
  }
  revision 2017-09-22 {
    description "Changed VM snapshot action to VM backup action";
  }
  revision 2017-06-07 {
     description "Removed use of imports to simplify version tracking";
  }
  revision 2017-05-14 {
    description "Added info property describing purpose of module.";
  }
  revision 2017-05-08 {
    description "Added description to tenant";
  }
  revision 2017-05-01 {
    description "Rename tenant attribute multi_vim to vim_mapping with default value as true.";
  }
  revision 2017-04-25 {
    description "change VM snapshot to VM backup action";
  }
  revision 2017-04-25 {
    description "Added VM snapshot action";
  }
  revision 2017-03-20 {
    description "Added choice of netmask or ip_prefix to address in allowed_address_pairs";
  }
  revision 2017-03-06 {
    description "Add multi_vim attribute to tenant.";
  }
  revision 2017-02-27 {
    description "Changed the volume type - can't re-use the esc_volume_deployment as it has volid as one of the key which the volume API does not need";
  }
  revision 2017-02-15 {
    description "Added support for volume directly under tenant";
  }
  revision 2017-01-10 {
    description "Service operation: deployment recovery";
  }
  revision 2016-12-02 {
    description "Normalize new LCS policy names";
  }
  revision 2016-11-28 {
    description "Generic LCS_NOTIFY policy action support";
  }
  revision 2016-11-11 {
    description "VM-level software update LCS support";
  }
  revision 2016-11-08 {
     description "Add new api filterLog to query for logs in escmanager with given parameters.";
  }
  revision 2016-10-18 {
    description "Update placement_group description";
  }
  revision 2016-10-18 {
     description "Remove container default bandwidth values from esc_interface.yang";
  }
  revision 2016-10-06 {
     description "add vim connector and user id in notification";
  }
  revision 2016-10-05 {
    description "Add reboot_time(esc_datamodle.yang)";
  }
  revision 2016-10-04 {
    description "Add more LCS conditions (esc_types.yang)";
  }
  revision 2016-09-23 {
     description "Add top level container esc_system_config containing vim_connectors";
  }
  revision 2016-08-04 {
     description "add extra vm info in notification";
  }
  revision 2016-07-28 {
     description "Added prefix choice for subnet masks";
  }
  revision 2016-07-21 {
     description "Added template_engine field to config data configuration to support no token replacement";
  }
  revision 2016-03-01 {
     description "Added support for recovery VM operations";
  }
  revision 2015-07-23 {
     description "Added support for Tenant Network creation-network directly under tenant";
  }
  revision 2015-07-14 {
    description "Added a new deployment model under tenant";
  }
  revision 2015-06-29 {
    description
      "ESC Datamodel change to support independent creation of
       images and flavors";
  }
  revision 2014-06-23 {
    description "Elastic Services Controller Module";
  }

  container esc_datamodel {

    description
      "Top-level container for all ESC database objects.";

    tailf:info "This module contains a collection of YANG definitions related to VM lifecycle management";

    leaf version {
      type types:escversion;
      config false;
      mandatory true;
      description "ESC version";
    }


    /*
     * This is editable by admin and tenants.
     * Tenant-A will not be able to read or write any configs of Tenant-B
     * Configs specified by the tenants are merged with the ones specified
     * by the admin. The values specified by the admin takes precedence.
     */

    container tenants {
      list tenant {
        key "name";
        description "List of tenants";
        leaf name {
          type types:escname;
          mandatory true;
        }
        leaf description {
          description "A description of the tenant";
          type string;
        }
        leaf managed_resource {
          type boolean;
          default true;
        }
        leaf vim_mapping {
          description
            "Attribute to specify if the tenant is an esc tenant or if it is
            mapped to a vim tenant";
          type boolean;
          default true;
        }
        uses extension:extension_list_definition;
        uses network:esc_network;
        uses volume:esc_tenant_volume;
        uses dm:tenant_dep_model;
      }
    }

    /*
     * This represents the external networks that are shared among all
     * the tenants. This is typically created by the admin of the
     * data center typically as part of infrastructure setup.
     * During deployment, the names of the network created here are
     * specified in the interfaces section to associate interfaces
     * wih these networks.
     */
    uses network:esc_network;

    /*
     * This contains the images and its attributes. This is created by
     * the admin or the ESC default tenant.
     */
    uses disk:esc_images;

    /*
     * This contains the flavors and its attributes. This is created by
     * the admin or the ESC default tenant.
     */
    uses flavor:esc_flavors;

    /*
     * This contains file server configurations.
     *
     */
    uses file_servers:esc_file_server;

    container opdata {
      presence "Indicates that ESC has exported some operational data";
      description
        "This contains all the operational data of the services that have been
         registered and/or instantiated. This is operational data,
         means it is READ-ONLY. Subtrees under this will inherit
         READ-ONLY property, thereby entire subtree becomes READ-ONLY";
      config false;
      tailf:callpoint opdata;
      uses op:esc_opdata;
    } /* END opdata */

    container info {
      presence "Indicates that ESC has exported its information";
      description
        "This contains all the information related to versions and copyrights";
      config false;
      tailf:callpoint opdata;
      uses info:esc_info;
    } /* END info */
  }

  rpc vimAction {
  	description "VIM connector actions including check_status.";
    tailf:actionpoint escrpc;
  	input {
      leaf actionType {
        mandatory true;
        description "VIM connector action type";
        type types:vim_action_types;
      }
	  leaf vimId {
        mandatory true;
        description "VIM connector Id";
        type types:escname;
      }
    }
  }

  rpc serviceAction {
    description "Service actions including stop, start, reboot, recover, disable-monitor and enable monitor.";
    tailf:actionpoint escrpc;
    tailf:hidden "none";
    input {
      leaf actionType {
        mandatory true;
        description "Service action type";
        type types:action_types;
      }
      leaf tenantName {
        mandatory true;
        description "Tenant Name";
        type types:escname;
      }
      leaf depName {
        mandatory true;
        description "Deployment Name";
        type types:escname;
      }
      leaf serviceName {
        mandatory true;
        description "Service Name";
        type types:escname;
      }
      leaf serviceVersion {
        mandatory true;
        description "Service Version";
        type types:escname;
      }
      uses property:property_list_definition;
    }
  }

  rpc serviceRestoration {
    description "Trigger Service deployment based on provided export/backUp archive";
    tailf:actionpoint escrpc;
    tailf:hidden "none";
    input {
      list import {
        leaf importPath {
          mandatory true;
          description "Path to backup/exported archive";
          type string;
        }

        leaf vm_group_name {
          description "VM group name to restore the backup for";
          type string;
        }
      }
    }
  }

  rpc vmImportAction {
    description "Trigger single vm deployment based on provided export/backUp archive";
    tailf:info "Import VM from backed-up VM archive.";
    tailf:actionpoint escrpc;
    input {
      leaf importPath {
          mandatory true;
          description "Path to backup/exported archive";
          tailf:info "This is the path to the backup file.";
          type string;
      }
      leaf uniqueMacUid {
          mandatory false;
          description "Enable to create unique MAC Addrs and UID on VM Import";
          tailf:info "Enable to create unique MAC Addr and UID on VM Import";
          type empty;
      }
    }
  }

  rpc vmAction {
    description "VM actions including stop, start, reboot, disable-monitor and enable monitor.";
    tailf:info "VM actions including stop, start, reboot, disable monitor and enable monitor";
    tailf:actionpoint escrpc;
    input {
      leaf actionType {
        mandatory true;
        description "VM action type";
        tailf:info "type: stop, start, reboot, disable monitor and enable monitor.";
        type types:action_types;
      }
      leaf vmName {
        mandatory true;
        description "VM Name";
        tailf:info "This is the VM name from deployment opdata.";
        type types:escname;
      }
    }
  }
  rpc calculateVMLCExportSize {
    description "RPC call to calculate size of vm, image and flavors backup size";
    tailf:info "RPC call to caluclate size of vm, image and flavors backup size";
    tailf:actionpoint escrpc;
    output {
      leaf size {
        description "Approximate size of image and flavors backup";
        tailf:info "Approximate size of image and flavors backup";
        type string;
      }
      leaf unit {
        description "Units of Size";
        tailf:info "Units of Size";
        type string;
      }
    }
  }

  rpc vmImageFlavorExport{
    description "ExportAction for Images and Flavors";
    tailf:info "Export all Images and Flavors in a host.";
    tailf:actionpoint escrpc;
    input {

    leaf imageName {
      mandatory false;
       description "Optional: VM Image Name.If provided,specified Image will be exported otherwise will export all the images and Flavors in the host. ";
       tailf:info "This is the VMImage name from VMImage opdata.";
       type types:escname;
     }
    leaf exportName{
       mandatory true;
       description "Export Name";
       tailf:info "This is the name for export file. No more than 256 Characters";
       type types:escname;
     }
      leaf exportPath {
        mandatory false;
        description
          "This is the path to the export directory. Accepted formats include:
           1.extdatastore<num>:<sub-path>  ex. extdatastore1:/intdatastore/uploads/
           2.intdatastore:<sub-path> ex. intdatastore:/uploads/
           3.nfs:<sub-path> ex. nfs:/extdatastore/tmp/
           4.usb:usb1<sub-path> ex. usb:/usb1/upload";
        tailf:info
          "This is the path to the backup directory. Accepted formats include:
          1.extdatastore<num>:<sub-path>  ex. extdatastore1:/uploads/
          2.intdatastore:<sub-path> ex. intdatastore:/uploads/
          3.nfs:<sub-path> ex. nfs:/extdatastore/tmp/
          4.usb:usb1<sub-path> ex. usb:/usb1/upload";
        type string;
        default "intdatastore:/uploads/";
      }
    }
  }
  rpc vmImageFlavorImport{
    description "Trigger vmImage and Flavor import based on provided export/backUp archive";
    tailf:info "Import VMImages and Flavors from backed-up VMImageFlavor archive.";
    tailf:actionpoint escrpc;
    input {
      leaf importPath {
        mandatory true;
        description "Path to backup/exported archive";
        tailf:info "This is the path to the backup file.";
        type string;
       }
   }
 }

  rpc vmBackupAction {
    description "VM Backup action";
    tailf:info "Backup a specified VM which is stopped.";
    tailf:actionpoint escrpc;
    input {
      leaf vmName {
        mandatory true;
        description "VM Name";
        tailf:info "This is the VM name from deployment opdata.";
        type types:escname;
      }

      leaf backupName {
        mandatory true;
        description "Backup Name";
        tailf:info "This is the name for the backup file. No more than 256 characters.";
        type types:escname;
      }

      leaf actionType {
        mandatory false;
        description "operation type: export, snapshot";
        type types:backup_action_type;
        default SNAPSHOT;
      }

      uses property:property_list_definition;
    }
  }


  rpc vmExportAction {
    description "VM backup action";
    tailf:info "Backup a specified VM which is stopped.";
    tailf:actionpoint escrpc;
    input {
      leaf vmName {
        mandatory true;
        description "VM Name";
        tailf:info "This is the VM name from deployment opdata.";
        type types:escname;
      }

      leaf exportName {
        mandatory true;
        description "Export Name";
        tailf:info "This is the name for the export file. No more than 256 characters.";
        type types:escname;
      }

      leaf exportPath {
          mandatory false;
          description
              "This is the path to the export directory. Accepted formats include:
               1.	extdatastore<num>:<sub-path>  ex. extdatastore1:/intdatastore/uploads/
               2.	intdatastore:<sub-path> ex. intdatastore:/uploads/
               3.	nfs:<sub-path> ex. nfs:/extdatastore/tmp/
               4.	usb:<sub-path> ex. usb:/tmp1/upload";
          tailf:info
              "This is the path to the backup directory. Accepted formats include:
               1.	extdatastore<num>:<sub-path>  ex. extdatastore1:/uploads/
               2.	intdatastore:<sub-path> ex. intdatastore:/uploads/
               3.	nfs:<sub-path> ex. nfs:/extdatastore/tmp/
               4.	usb:<sub-path> ex. usb:/tmp1/upload";
          type string;
          default "intdatastore:/uploads/";
      }
      leaf includeImage {
          mandatory false;
          description "Enable to include VM image & flavor in VM Export";
          tailf:info "Enable to include VM image & flavor in VM Export";
          type empty;
      }
      uses property:property_list_definition;
    }
  }



  rpc recoveryVmAction {
    description "Recovery VM actions including do and donot.";
    tailf:info "Recovery VM actions can recover a specified VM";
    tailf:actionpoint escrpc;
    tailf:hidden "none";
    input {
      leaf actionType {
        mandatory true;
        description "Recovery VM action type";
        tailf:info "Recovery VM action type: DO";
        type types:recovery_op_types;
      }
      leaf vmName {
        mandatory true;
        description "VM Name";
        tailf:info "VM name";
        type types:escname;
      }
      leaf checkVmBeforeRecovery {
        mandatory false;
        description "checking Vm reachable before doing recovery actions";
        type boolean;
        default false;
      }
      uses property:property_list_definition;
    }
  }

  rpc hostAction {
    description "Host actions including enable and disable";
    tailf:info "Enable or disable compute host for VIM";
    tailf:actionpoint escrpc;
    tailf:hidden "none";
    input {
      leaf actionType {
        mandatory true;
        description "VM action type";
        tailf:info "Host actions including enable and disable";
        type types:host_action_type;
      }
      leaf hostName {
        mandatory true;
        description "Host Name";
        tailf:info "Specify a host name";
        type types:escname;
      }
    }
  }
  rpc vmMigrate {
	    description "Trigger vm migrate to support DPDK";
	    tailf:actionpoint escrpc;
	    input {
	    	leaf migrateAction {
	          description "Action to enable DPDK";
	          type types:migrateAction;
	        }

	    	 leaf vmName {
	    	     mandatory true;
	    		 description "VM Name";
	    	     tailf:info "This is the VM name from deployment opdata.";
	    	     type types:escname;
	    	 }
	    	 leaf vmStart {
	             type boolean;
	             default true;
	           }
	    }
	  }



  rpc filterLog {
    description "Query and filter escmanager logs using given parameters";
    tailf:actionpoint escrpc;
    tailf:hidden "none";
    tailf:info "Query and filter escmanager logs using given parameters";
    input {
      leaf log_level {
        mandatory false;
        description "One of DEBUG / INFO / WARN / ERROR / TRACE / FATAL. Results will include all logs at and
                     above the level specified";
        tailf:info "One of DEBUG / INFO / WARNING / ERROR / TRACE / FATAL. Results will include all logs at and
                     above the level specified";
        type types:log_level_types;
        default ERROR;
      }
      leaf log_count {
        mandatory false;
        description "Number of logs to return";
        tailf:info "Number of logs to return";
        type uint32;
        default 10;
      }
      container classifications {
        leaf-list classification {
          description "Classification values to be used for the log filtering.  For example: 'OS', 'SM'.
                      Logs containing any of the provided classification values will be returned.";
          tailf:info "Classification values to be used for the log filtering.  For example: 'OS', 'SM'.
                      Logs containing any of the provided classification values will be returned.";
          type types:log_classification_types;
        }
      }
      container tags {
	      list tag {
          key "name";
          leaf name {
            mandatory true;
            description "Tag name to be used for the log filtering.  For example: 'tenant', 'depName'.
                         Logs containing any of the provided tag name plus the tag values will be returned.";
            tailf:info "Tag name to be used for the log filtering.  For example: 'tenant', 'depName'.
                         Logs containing any of the provided tag name plus the tag values will be returned.";
            type types:log_tag_types;
          }
          leaf value {
            mandatory true;
            description "Tag value pairs to be used for the log filtering.  For example: 'adminTenant', 'CSRDeployment'";
            tailf:info "Tag value pairs to be used for the log filtering.  For example: 'adminTenant', 'CSRDeployment'";
            type string;
          }
        }
      }
    }
    output {
      container filterLogResults {
        leaf log_level {
          description "Log level used to filter for the logs.";
          tailf:info "Log level used to filter for the logs.";
          type types:log_level_types;
        }
        list logs {
          container classifications {
            leaf-list classification {
              description "Classifications used to filter for the logs.";
              tailf:info "Classifications used to filter for the logs.";
              type types:log_classification_types;
            }
          }
          container tags {
            list tag {
              key "name";
              leaf name {
                mandatory true;
                description "Tag name used to filter for the logs.";
                tailf:info "Tag name used to filter for the logs.";
                type types:log_tag_types;
              }
              leaf value {
                mandatory true;
                description "Tag value used to filter for the logs.";
                tailf:info "Tag value used to filter for the logs.";
                type string;
              }
            }
          }
          leaf log_date_time {
            description "Timestamp of the log.";
            tailf:info "Timestamp of the log.";
            type string;
          }
          leaf log_message {
            description "The log message.";
            tailf:info "The log message.";
            type string;
          }
        }
      }
    }
  }


rpc importDeploymentData {
  description "Provide imported resources data for a Deployment";
  tailf:actionpoint escrpc;
  input {

      leaf action_type {
        mandatory true;
        description "import data action to perform";
        type types:import_action_types;

      }

      leaf project_name {
        mandatory true;
        description "tenant/project name that owns the VM(s)";
        type types:escname;

      }

      leaf deployment_name {
        mandatory true;
        description "the deployment name to use for the esc deployment datamodel for this import.";
        type types:escname;
      }

      leaf payload_path {
        description "the  path to the imported data .xml file.";
        type string;

        must "../action_type = 'CREATE'  or ../action_type = 'create'" {
          error-message "payload path must be provided for import CREATE action only";
        }
      }

  }
  output {
      anyxml imported_data {
        description " the imported data payload";
      }
  }
}
  container esc_system_config {
    description "Top-level container for all ESC system configs.";

    /*
     * This contains the virtual infrastructure managers registered
     * with  ESC and information for connecting to them.
     */
    uses vim:esc_vim_connector;
    uses configparams:esc_config_parameter;
  }


}
