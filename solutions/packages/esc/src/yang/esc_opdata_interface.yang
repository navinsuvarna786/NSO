module esc_opdata_interface {

  /*
   * This represents operational data of the interfaces of the VM
   */

  namespace "http://www.cisco.com/esc/esc_opdata_interface";


  prefix "esc_opdata_interface";

  import esc_types { prefix "types"; }

  organization "Cisco Systems";

  contact "Shesha Sreenivasamurthy <shesha@cisco.com>";

  revision 2020-06-18 {
    description "Adding admin_state_up to interface";
  }

  revision 2020-02-13 {
    description "Adding binding_profile to interface";
  }

  revision 2018-11-14 {
    description "Adding source bridge to interface";
  }

  revision 2018-03-28 {
    description "Added address_id to address list and renamed address_info to address";
  }

  revision 2018-03-05 {
    description "Added public_ip_address within interface";
  }

  revision 2018-03-02 {
    description "Added grouping for esc_opdata_interface_addresses within interface to support interface with multiple addresses";
  }

  revision 2017-11-01 {
    description "Added port_security_enabled within interface";
  }
  revision 2017-08-04 {
    description "Added vim_interface_name within interface";
  }

  revision 2016-04-27 {
    description "Adding type to the interface";
  }
  revision 2016-01-25 {
    description "Adding model to the interface";
  }
  revision 2015-11-09 {
    description "Added security groups leaf for the interface";
  }
  revision 2015-08-31 {
    description "Altering id types for port, network and subnet to be strings rather than UUIDs";
  }
  revision 2015-07-02 {
    description "Added netmask and gateway to the interface";
  }
  revision 2015-06-18 {
    description "Added port_forwards";
  }
  revision 2014-12-03 {
    description "Added NIC ID to the interface and changed the key";
  }
  revision 2014-08-06 {
    description "Elastic Services Controller Module's tenant's interface's
                operational data";
  }

  grouping esc_opdata_interface_addresses {
    description "This contains a list of the unique fields per address";
    list address {
      description "list of address";
      key "address_id";
      leaf address_id {
        description "Id for the address in address list.";
        type uint16;
        mandatory true;
      }
      leaf subnet {
        description "Sub network to which this interface is attached";
        type string;
      }
      leaf ip_address {
        description "IP address for this interface";
        type types:escipaddr;
      }
      leaf prefix {
        description "Prefix of the subnet (CIDR)";
        type types:esc_ip_prefix;
      }
      leaf gateway {
        description "Gateway of the subnet";
        type types:escipaddr;
      }
    }
  }

  grouping esc_opdata_interface {
    description
      "This contains all the operational data of the interface for each VM";
    container interfaces {
      list interface {
        key "nicid";
        description "Interface running information";
        leaf nicid {
          description "ID of the interface specified during configuration";
          type uint16;
        }
        leaf model {
          description
            "In case of virtual: e1000, virtio etc. In case of passthrough:
             Model of the NIC. This will be specific to the data center. Data
             centers may have NICs that support virtual functions from
             different vendors, like Intel, Cisco etc.";
          type types:iface_model;
        }
        leaf type {
          description "Interface Type: virtual/passthru";
          type string;
        }
        leaf vim_interface_name {
          description "User specified name for the interface on the VIM";
          type types:escname;
        }
        leaf port_id {
          description "Port identifier";
          type string;
        }
        leaf admin_state_up {
          description "The administrative state of the resource, which is up (true) or down (false).";
          type boolean;
        }
        leaf network {
          description "Network to which this interface is attached";
          type string;
        }
        leaf subnet {
          description "Sub Network to which this interface is attached";
          type string;
        }
        leaf ip_address {
          description "IP address for this interface";
          type types:escipaddr;
        }
        leaf public_ip_address {
          description "Public IP address for this interface";
          type types:escipaddr;
        }
        leaf mac_address {
          description "MAC address for this interface";
          type types:escmacaddr;
        }
        leaf port_security_enabled {
          description "Whether the port security is enabled at port level";
          type boolean;
        }
        leaf netmask {
          description "Netmask of the subnet";
          type types:escipaddr;
        }
        leaf gateway {
          description "Gateway of the subnet";
          type types:escipaddr;
        }
        leaf security_groups {
          description "List of delimiter-separated security groups for the interface";
          type string;
        }
        container port_forwards {
          description "This section contains teh forwarded prts on this interface";
          list port_forward {
            key "port_type";
            leaf port_type {
              description "Purpose of the forwarded port. For example ssh, telnet, etc.";
              type string;
            }
            leaf port_number {
              description "The external port number for this interface";
              type uint16;
            }
            leaf source_bridge {
              description "Bridge that will be used to access the server externally.";
              type string;
            }
          }
        }
        container binding_profile {
        list property {
            key "name";
            description "Binding profile property";
            leaf name {
                description "Property name";
                type string;
                mandatory true;
            }
            leaf value {
                description "Property value";
                type string;
            }
          }
        }
        uses esc_opdata_interface_addresses;
      }
    }
  }
}
