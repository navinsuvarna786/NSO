module esc_opdata {
  
  /*
   * This is the top level YANG module for ESC's operational data.
     This imports other
   * submodules as required.
   */
  namespace "http://www.cisco.com/esc/esc_opdata";

  prefix "esc_opdata";

  import esc_opdata_tenant { prefix "optenant"; }
  import esc_opdata_devstats { prefix "opstats"; }
  import esc_opdata_networks { prefix "opnetworks"; }
  import esc_opdata_images { prefix "opimages"; }
  import esc_opdata_flavors { prefix "opflavors"; }
  import esc_opdata_system_config { prefix "opsysconf"; }
  import esc_opdata_default_locators { prefix "oplocators"; }

  organization "Cisco Systems";

  contact "Shesha Sreenivasamurthy <shesha@cisco.com>";

  revision 2016-04-01 {
    description "Add ESC Default locators details ";
  }  
  revision 2016-02-01 {
    description "Add ESC System configuration details ";
  }
  revision 2015-07-06 {
    description "Add operational data for images and flavors";
  }
  revision 2014-08-06 {
    description "Elastic Services Controller Module's operational data";
  }

  grouping esc_opdata {
    leaf status {
      description "Status of ESC";
      type string;
    }

    /* ESC VM statstics */
    uses opstats:esc_opdata_devstats;

    /* ESC system config parameters */
    uses opsysconf:esc_opdata_system_config;
    
    /* ESC default VIM-locators parameters */
    uses oplocators:esc_opdata_default_locators;

    /* Shared networks created at admin tenant */
    uses opnetworks:esc_opdata_networks;
    
    /* Public images created at admin tenant */
    uses opimages:esc_opdata_images;
    
    /* Public flavors created at admin tenant */
    uses opflavors:esc_opdata_flavors;

    /* Opdata of the VNFs spun by ESC */
    uses optenant:esc_opdata_tenant;
  }
}
