module esc_port_forwarding {


  namespace "http://www.cisco.com/esc/esc_port_forwarding";
  prefix "esc_port_forwarding";


  organization "Cisco Systems";

  contact "Shesha Sreenivasamurthy <shesha@cisco.com>";

  description
    "ESC's port forwarding descriptions'";

  revision 2017-05-08 {
    description "added source_bridge";
  }
  revision 2015-06-08 {
    description "added esc_port_forwarding";
  }

  grouping esc_port_forwarding {
    container port_forwarding {
      description
        "This section allows for specifying port(s) to be forwarded 
         externally.";
      list port {
        key "type";
        leaf type {
          description
            "Type or purpose of the port to be forwarded";
          type string;
          mandatory true;
        }
        leaf protocol {
          description
            "Protocol type of traffic to be forwarded";
          type string;
          mandatory true;
        }
        leaf vnf_port {
          description
            "Internal port of VNF to be exposed externally.";
          type uint16;
          mandatory true;
        }
        leaf source_bridge {
          description
            "Bridge that will be used to access the server externally.";
          type string;
          default "wan-br";
        }
        list external_port_range {
          key "start end";
          description
            "Contiguous block of external ports can be specified using range.";
          leaf start {
            description "Starting external port in the range";
            type uint16;
          }
          leaf end {
            description "Ending external port in the range";
            type uint16;
          }
        }
      }
    }
  }
}
