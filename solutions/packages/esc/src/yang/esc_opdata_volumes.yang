module esc_opdata_volumes {

  /*
   * This represents operational data of the volumes attached to a VM
   */

  namespace "http://www.cisco.com/esc/esc_opdata_volumes";

  prefix "esc_opdata_volumes";


  import ietf-yang-types { prefix "ietf-yang-types"; }
  import esc_types { prefix "types"; }


  organization "Cisco Systems";

  revision 2019-01-29 {
    description "Added Tenant and Deployment Volume lists.";     
  }

  revision 2016-11-30 {
    description "Added image and volid to Volume list.";     
  }

  revision 2016-01-19 {
    description "Added boot_index to Volume list.";
  }

  grouping esc_opdata_volume_details{

        leaf external_id {
          description "UUID of the volume in the VIM.";
          type ietf-yang-types:uuid;
        }
        
        leaf bus {
          description "Block device bus to be used: ide, scsi, virtio";
          type string;
        }
        
        leaf type {
          description "Type of the volume attached.";
          type types:escname;
        }
        
        leaf size {
          description "Size of the Volume with unit.";
          type string;
        }

        leaf boot_index {
          description "Specify the boot order for bootable volumes.";
          type string;
        }
        
        leaf image {
          description "Name or UUID of the source image";
          type string;
        }
  }


  grouping esc_opdata_tenant_volumes{

      
    container volumes {
      list volume {
        key "display_name";
        
	description "Volume running information";
        
        leaf display_name {
          description "Display name of the Volume";
          type types:escname;
        }
        leaf volid {
          description "Volumes will be presented to the VM sorted by volume ID";
          type uint16;
        } 
	uses esc_opdata_volume_details;
      }
    }
  }

  grouping esc_opdata_deployment_volumes {

    description
      "This contains all the operational data of the volumes for each VM";
      
    container volumes {
      list volume {
        key "volid";
        leaf volid {
          description "Volumes will be presented to the VM sorted by volume ID";
          type uint16;
        } 
        leaf display_name {
          description "Display name of the Volume";
          type types:escname;
        }
       	uses esc_opdata_volume_details;

        
        leaf format {
          description "Format of the disk to create.";
          type types:disk_formats;
        }

        leaf device_type {
          description "Type of device being attached to the VM.";
          type types:device_type;
        }

        leaf storage_location {
          description "Location of the storage volume.";
          type string;
        }

      }
    }
  }
}
